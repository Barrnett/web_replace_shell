--
-- EZWELL-IFVCG-MIB.mib
-- MIB generated by MG-SOFT Visual MIB Builder Version 6.0  Build 88
-- Thursday, October 08, 2015 at 01:04:50
--

--  EZWELL-IFVCG-MIB.mib
-- MIB generated by MG-SOFT Visual MIB Builder Version 6.0  Build 88
-- Monday, September 28, 2015 at 23:33:38
-- 
--  EZWELL-IFVCG-MIB.mib
-- MIB generated by MG-SOFT Visual MIB Builder Version 6.0  Build 88
-- Monday, September 28, 2015 at 23:20:31
-- 
--  EZWELL-IFVCG-MIB.mib
-- MIB generated by MG-SOFT Visual MIB Builder Version 6.0  Build 88
-- Monday, September 28, 2015 at 15:51:23
-- 
--  Easy BroadBand Technology MIB VER 2.0 (date 2009.10.1)
-- 
-- Easy BroadBand Technology specific MIB for VCG channel property.
-- dated  2009.10.1
-- Version 2.0 

	EZWELL-IFVCG-MIB DEFINITIONS ::= BEGIN
 
		IMPORTS
			eciESDeviceIndex			
				FROM EZWELL-ELEMENTSTRUCTURE-MIB			
			eciInterfaceModule			
				FROM EZWELL-GENERAL-MODEL-MIB			
			DisplayString			
				FROM RFC1213-MIB			
			OBJECT-TYPE			
				FROM SNMPv2-SMI;
	
	
	
--
-- Node definitions
--
	
--  Node definitions
-- 
-- Node definitions
-- 
-- Node definitions
-- 
-- 1.3.6.1.4.1.25449.1.1.8.5
-- 1.3.6.1.4.1.25449.1.1.8.5
-- 1.3.6.1.4.1.25449.1.1.8.5
		-- 1.3.6.1.4.1.25449.1.1.8.5
		eciIfMdVCG OBJECT IDENTIFIER ::= { eciInterfaceModule 5 }

		
--    1.3.6.1.4.1.25449.1.1.8.5.1
-- 1.3.6.1.4.1.25449.1.1.8.5.1
-- 1.3.6.1.4.1.25449.1.1.8.5.1
		-- 1.3.6.1.4.1.25449.1.1.8.5.1
		eciIfMdVCGNumberTable OBJECT-TYPE
			SYNTAX SEQUENCE OF EciIfMdVCGNumberEntry
			MAX-ACCESS not-accessible
			STATUS current
			DESCRIPTION
				" "
			::= { eciIfMdVCG 1 }

		
--    1.3.6.1.4.1.25449.1.1.8.5.1.1
-- 1.3.6.1.4.1.25449.1.1.8.5.1.1
-- 1.3.6.1.4.1.25449.1.1.8.5.1.1
		-- 1.3.6.1.4.1.25449.1.1.8.5.1.1
		eciIfMdVCGNumberEntry OBJECT-TYPE
			SYNTAX EciIfMdVCGNumberEntry
			MAX-ACCESS not-accessible
			STATUS current
			DESCRIPTION
				" "
			INDEX { eciESDeviceIndex }
			::= { eciIfMdVCGNumberTable 1 }

		
		EciIfMdVCGNumberEntry ::=
			SEQUENCE { 
				eciIfMdVCGNumber
					INTEGER
			 }

--    1.3.6.1.4.1.25449.1.1.8.5.1.1.1
-- 1.3.6.1.4.1.25449.1.1.8.5.1.1.1
-- 1.3.6.1.4.1.25449.1.1.8.5.1.1.1
		-- 1.3.6.1.4.1.25449.1.1.8.5.1.1.1
		eciIfMdVCGNumber OBJECT-TYPE
			SYNTAX INTEGER (0..63)
			MAX-ACCESS read-only
			STATUS current
			DESCRIPTION
				" "
			::= { eciIfMdVCGNumberEntry 1 }

		
--     VCG channel list entry
-- 1.3.6.1.4.1.25449.1.1.8.5.2
-- 1.3.6.1.4.1.25449.1.1.8.5.2
-- 1.3.6.1.4.1.25449.1.1.8.5.2
		-- 1.3.6.1.4.1.25449.1.1.8.5.2
		eciIfMdVCGChannelTable OBJECT-TYPE
			SYNTAX SEQUENCE OF EciIfMdVCGChannelEntry
			MAX-ACCESS not-accessible
			STATUS current
			DESCRIPTION
				"VCG channel list table"
			::= { eciIfMdVCG 2 }

		
--    1.3.6.1.4.1.25449.1.1.8.5.2.1
-- 1.3.6.1.4.1.25449.1.1.8.5.2.1
-- 1.3.6.1.4.1.25449.1.1.8.5.2.1
		-- 1.3.6.1.4.1.25449.1.1.8.5.2.1
		eciIfMdVCGChannelEntry OBJECT-TYPE
			SYNTAX EciIfMdVCGChannelEntry
			MAX-ACCESS not-accessible
			STATUS current
			DESCRIPTION
				"VCG channel list table entry"
			INDEX { eciESDeviceIndex, eciIfMdVCGChannelIndex }
			::= { eciIfMdVCGChannelTable 1 }

		
		EciIfMdVCGChannelEntry ::=
			SEQUENCE { 
				eciIfMdVCGChannelIndex
					INTEGER,
				eciIfMdVCGChannelName
					DisplayString,
				eciIfMdVCGChannelSerialN
					INTEGER,
				eciIfMdVCGChannelLCASEnabled
					INTEGER,
				eciIfMdVCGChannelMemberNumber
					INTEGER,
				eciIfMdVCGChannelEnabled
					INTEGER,
				eciIfMdOperationIfNMChannel
					INTEGER
			 }

--    1.3.6.1.4.1.25449.1.1.8.5.2.1.1
-- 1.3.6.1.4.1.25449.1.1.8.5.2.1.1
-- 1.3.6.1.4.1.25449.1.1.8.5.2.1.1
		-- 1.3.6.1.4.1.25449.1.1.8.5.2.1.1
		eciIfMdVCGChannelIndex OBJECT-TYPE
			SYNTAX INTEGER
				{
				vcg-1(1281),
				vcg-2(1282),
				vcg-3(1283),
				vcg-4(1284),
				vcg-5(1285),
				vcg-6(1286),
				vcg-7(1287),
				vcg-8(1288),
				vcg-9(1289),
				vcg-10(1290),
				vcg-11(1291),
				vcg-12(1292),
				vcg-13(1293),
				vcg-14(1294),
				vcg-15(1295),
				vcg-16(1296),
				vcg-17(1537),
				vcg-18(1538),
				vcg-19(1539),
				vcg-20(1540),
				vcg-21(1541),
				vcg-22(1542),
				vcg-23(1543),
				vcg-24(1544),
				vcg-25(1545),
				vcg-26(1546),
				vcg-27(1547),
				vcg-28(1548),
				vcg-29(1549),
				vcg-30(1550),
				vcg-31(1551),
				vcg-32(1552),
				vcg-33(1793),
				vcg-34(1794),
				vcg-35(1795),
				vcg-36(1796),
				vcg-37(1797),
				vcg-38(1798),
				vcg-39(1799),
				vcg-40(1800),
				vcg-41(1801),
				vcg-42(1802),
				vcg-43(1803),
				vcg-44(1804),
				vcg-45(1805),
				vcg-46(1806),
				vcg-47(1807),
				vcg-48(1808),
				vcg-49(2049),
				vcg-50(2050),
				vcg-51(2051),
				vcg-52(2052),
				vcg-53(2053),
				vcg-54(2054),
				vcg-55(2055),
				vcg-56(2056),
				vcg-57(2057),
				vcg-58(2058),
				vcg-59(2059),
				vcg-60(2060),
				vcg-61(2061),
				vcg-62(2062),
				vcg-63(2063),
				vcg-64(2064)
				}
			MAX-ACCESS read-only
			STATUS current
			DESCRIPTION
				"VCG channel unique index"
			::= { eciIfMdVCGChannelEntry 1 }

		
--    1.3.6.1.4.1.25449.1.1.8.5.2.1.2
-- 1.3.6.1.4.1.25449.1.1.8.5.2.1.2
-- 1.3.6.1.4.1.25449.1.1.8.5.2.1.2
		-- 1.3.6.1.4.1.25449.1.1.8.5.2.1.2
		eciIfMdVCGChannelName OBJECT-TYPE
			SYNTAX DisplayString (SIZE (0..31))
			MAX-ACCESS read-only
			STATUS current
			DESCRIPTION
				"VCG channel name"
			::= { eciIfMdVCGChannelEntry 2 }

		
--    1.3.6.1.4.1.25449.1.1.8.5.2.1.3
-- 1.3.6.1.4.1.25449.1.1.8.5.2.1.3
-- 1.3.6.1.4.1.25449.1.1.8.5.2.1.3
		-- 1.3.6.1.4.1.25449.1.1.8.5.2.1.3
		eciIfMdVCGChannelSerialN OBJECT-TYPE
			SYNTAX INTEGER
			MAX-ACCESS read-only
			STATUS current
			DESCRIPTION
				"VCG channel serial no."
			::= { eciIfMdVCGChannelEntry 3 }

		
--    1.3.6.1.4.1.25449.1.1.8.5.2.1.4
-- 1.3.6.1.4.1.25449.1.1.8.5.2.1.4
-- 1.3.6.1.4.1.25449.1.1.8.5.2.1.4
		-- 1.3.6.1.4.1.25449.1.1.8.5.2.1.4
		eciIfMdVCGChannelLCASEnabled OBJECT-TYPE
			SYNTAX INTEGER
			MAX-ACCESS read-only
			STATUS current
			DESCRIPTION
				" "
			::= { eciIfMdVCGChannelEntry 4 }

		
--    1.3.6.1.4.1.25449.1.1.8.5.2.1.5
-- 1.3.6.1.4.1.25449.1.1.8.5.2.1.5
-- 1.3.6.1.4.1.25449.1.1.8.5.2.1.5
		-- 1.3.6.1.4.1.25449.1.1.8.5.2.1.5
		eciIfMdVCGChannelMemberNumber OBJECT-TYPE
			SYNTAX INTEGER
			MAX-ACCESS read-only
			STATUS current
			DESCRIPTION
				" "
			::= { eciIfMdVCGChannelEntry 5 }

		
--    1.3.6.1.4.1.25449.1.1.8.5.2.1.6
-- 1.3.6.1.4.1.25449.1.1.8.5.2.1.6
-- 1.3.6.1.4.1.25449.1.1.8.5.2.1.6
		-- 1.3.6.1.4.1.25449.1.1.8.5.2.1.6
		eciIfMdVCGChannelEnabled OBJECT-TYPE
			SYNTAX INTEGER
				{
				disable(0),
				enable(1)
				}
			MAX-ACCESS read-only
			STATUS current
			DESCRIPTION
				" "
			::= { eciIfMdVCGChannelEntry 6 }

		
--    1.3.6.1.4.1.25449.1.1.8.5.2.1.7
-- 1.3.6.1.4.1.25449.1.1.8.5.2.1.7
-- 1.3.6.1.4.1.25449.1.1.8.5.2.1.7
		-- 1.3.6.1.4.1.25449.1.1.8.5.2.1.7
		eciIfMdOperationIfNMChannel OBJECT-TYPE
			SYNTAX INTEGER
				{
				normalPort(0),
				nmPort(1)
				}
			MAX-ACCESS read-only
			STATUS current
			DESCRIPTION
				" "
			::= { eciIfMdVCGChannelEntry 7 }

		
--     VCG channel status entry
-- 1.3.6.1.4.1.25449.1.1.8.5.3
-- 1.3.6.1.4.1.25449.1.1.8.5.3
-- 1.3.6.1.4.1.25449.1.1.8.5.3
		-- 1.3.6.1.4.1.25449.1.1.8.5.3
		eciIfMdVCGStatusTable OBJECT-TYPE
			SYNTAX SEQUENCE OF EciIfMdVCGStatusEntry
			MAX-ACCESS not-accessible
			STATUS current
			DESCRIPTION
				"VCG channel status table"
			::= { eciIfMdVCG 3 }

		
--    1.3.6.1.4.1.25449.1.1.8.5.3.1
-- 1.3.6.1.4.1.25449.1.1.8.5.3.1
-- 1.3.6.1.4.1.25449.1.1.8.5.3.1
		-- 1.3.6.1.4.1.25449.1.1.8.5.3.1
		eciIfMdVCGStatusEntry OBJECT-TYPE
			SYNTAX EciIfMdVCGStatusEntry
			MAX-ACCESS not-accessible
			STATUS current
			DESCRIPTION
				"VCG channel status table entry"
			INDEX { eciESDeviceIndex, eciIfMdVCGChannelIndex }
			::= { eciIfMdVCGStatusTable 1 }

		
		EciIfMdVCGStatusEntry ::=
			SEQUENCE { 
				eciIfMdVCGStNoMember
					INTEGER,
				eciIfMdVCGStLCASMemberDIS
					INTEGER,
				eciIfMdVCGStSyncLoss
					INTEGER,
				eciIfMdVCGStUPIMismatch
					INTEGER
			 }

--    1.3.6.1.4.1.25449.1.1.8.5.3.1.1
-- 1.3.6.1.4.1.25449.1.1.8.5.3.1.1
-- 1.3.6.1.4.1.25449.1.1.8.5.3.1.1
		-- 1.3.6.1.4.1.25449.1.1.8.5.3.1.1
		eciIfMdVCGStNoMember OBJECT-TYPE
			SYNTAX INTEGER
			MAX-ACCESS read-only
			STATUS current
			DESCRIPTION
				" "
			::= { eciIfMdVCGStatusEntry 1 }

		
--    1.3.6.1.4.1.25449.1.1.8.5.3.1.2
-- 1.3.6.1.4.1.25449.1.1.8.5.3.1.2
-- 1.3.6.1.4.1.25449.1.1.8.5.3.1.2
		-- 1.3.6.1.4.1.25449.1.1.8.5.3.1.2
		eciIfMdVCGStLCASMemberDIS OBJECT-TYPE
			SYNTAX INTEGER
			MAX-ACCESS read-only
			STATUS current
			DESCRIPTION
				" "
			::= { eciIfMdVCGStatusEntry 2 }

		
--    1.3.6.1.4.1.25449.1.1.8.5.3.1.3
-- 1.3.6.1.4.1.25449.1.1.8.5.3.1.3
-- 1.3.6.1.4.1.25449.1.1.8.5.3.1.3
		-- 1.3.6.1.4.1.25449.1.1.8.5.3.1.3
		eciIfMdVCGStSyncLoss OBJECT-TYPE
			SYNTAX INTEGER
			MAX-ACCESS read-only
			STATUS current
			DESCRIPTION
				" "
			::= { eciIfMdVCGStatusEntry 3 }

		
--    1.3.6.1.4.1.25449.1.1.8.5.3.1.4
-- 1.3.6.1.4.1.25449.1.1.8.5.3.1.4
-- 1.3.6.1.4.1.25449.1.1.8.5.3.1.4
		-- 1.3.6.1.4.1.25449.1.1.8.5.3.1.4
		eciIfMdVCGStUPIMismatch OBJECT-TYPE
			SYNTAX INTEGER
			MAX-ACCESS read-only
			STATUS current
			DESCRIPTION
				" "
			::= { eciIfMdVCGStatusEntry 4 }

		
--     VCG channel config entry
-- 1.3.6.1.4.1.25449.1.1.8.5.4
-- 1.3.6.1.4.1.25449.1.1.8.5.4
-- 1.3.6.1.4.1.25449.1.1.8.5.4
		-- 1.3.6.1.4.1.25449.1.1.8.5.4
		eciIfMdVCGConfigTable OBJECT-TYPE
			SYNTAX SEQUENCE OF EciIfMdVCGConfigEntry
			MAX-ACCESS not-accessible
			STATUS current
			DESCRIPTION
				"VCG channel  table"
			::= { eciIfMdVCG 4 }

		
--    1.3.6.1.4.1.25449.1.1.8.5.4.1
-- 1.3.6.1.4.1.25449.1.1.8.5.4.1
-- 1.3.6.1.4.1.25449.1.1.8.5.4.1
		-- 1.3.6.1.4.1.25449.1.1.8.5.4.1
		eciIfMdVCGConfigEntry OBJECT-TYPE
			SYNTAX EciIfMdVCGConfigEntry
			MAX-ACCESS not-accessible
			STATUS current
			DESCRIPTION
				"VCG channel table entry"
			INDEX { eciESDeviceIndex, eciIfMdVCGChannelIndex }
			::= { eciIfMdVCGConfigTable 1 }

		
		EciIfMdVCGConfigEntry ::=
			SEQUENCE { 
				eciIfMdGFPConfigTxPFI
					INTEGER,
				eciIfMdGFPConfigRxPFI
					INTEGER,
				eciIfMdGFPConfigRxUPI
					INTEGER,
				eciIfMdGFPConfigRxEXI
					INTEGER,
				eciIfMdGFPConfigPFCSEnable
					INTEGER
			 }

--    1.3.6.1.4.1.25449.1.1.8.5.4.1.1
-- 1.3.6.1.4.1.25449.1.1.8.5.4.1.1
-- 1.3.6.1.4.1.25449.1.1.8.5.4.1.1
		-- 1.3.6.1.4.1.25449.1.1.8.5.4.1.1
		eciIfMdGFPConfigTxPFI OBJECT-TYPE
			SYNTAX INTEGER
			MAX-ACCESS read-only
			STATUS current
			DESCRIPTION
				" "
			::= { eciIfMdVCGConfigEntry 1 }

		
--    1.3.6.1.4.1.25449.1.1.8.5.4.1.2
-- 1.3.6.1.4.1.25449.1.1.8.5.4.1.2
-- 1.3.6.1.4.1.25449.1.1.8.5.4.1.2
		-- 1.3.6.1.4.1.25449.1.1.8.5.4.1.2
		eciIfMdGFPConfigRxPFI OBJECT-TYPE
			SYNTAX INTEGER
			MAX-ACCESS read-only
			STATUS current
			DESCRIPTION
				" "
			::= { eciIfMdVCGConfigEntry 2 }

		
--    1.3.6.1.4.1.25449.1.1.8.5.4.1.3
-- 1.3.6.1.4.1.25449.1.1.8.5.4.1.3
-- 1.3.6.1.4.1.25449.1.1.8.5.4.1.3
		-- 1.3.6.1.4.1.25449.1.1.8.5.4.1.3
		eciIfMdGFPConfigRxUPI OBJECT-TYPE
			SYNTAX INTEGER
			MAX-ACCESS read-only
			STATUS current
			DESCRIPTION
				" "
			::= { eciIfMdVCGConfigEntry 3 }

		
--    1.3.6.1.4.1.25449.1.1.8.5.4.1.4
-- 1.3.6.1.4.1.25449.1.1.8.5.4.1.4
-- 1.3.6.1.4.1.25449.1.1.8.5.4.1.4
		-- 1.3.6.1.4.1.25449.1.1.8.5.4.1.4
		eciIfMdGFPConfigRxEXI OBJECT-TYPE
			SYNTAX INTEGER
			MAX-ACCESS read-only
			STATUS current
			DESCRIPTION
				" "
			::= { eciIfMdVCGConfigEntry 4 }

		
--    1.3.6.1.4.1.25449.1.1.8.5.4.1.5
-- 1.3.6.1.4.1.25449.1.1.8.5.4.1.5
-- 1.3.6.1.4.1.25449.1.1.8.5.4.1.5
		-- 1.3.6.1.4.1.25449.1.1.8.5.4.1.5
		eciIfMdGFPConfigPFCSEnable OBJECT-TYPE
			SYNTAX INTEGER
			MAX-ACCESS read-only
			STATUS current
			DESCRIPTION
				" "
			::= { eciIfMdVCGConfigEntry 5 }

		
--      VCG channel performance entry      
-- 1.3.6.1.4.1.25449.1.1.8.5.5
-- 1.3.6.1.4.1.25449.1.1.8.5.5
-- 1.3.6.1.4.1.25449.1.1.8.5.5
		-- 1.3.6.1.4.1.25449.1.1.8.5.5
		eciIfMdVCGPerformanceTable OBJECT-TYPE
			SYNTAX SEQUENCE OF EciIfMdVCGPerformanceEntry
			MAX-ACCESS not-accessible
			STATUS current
			DESCRIPTION
				"VCG channel  table"
			::= { eciIfMdVCG 5 }

		
--    1.3.6.1.4.1.25449.1.1.8.5.5.1
-- 1.3.6.1.4.1.25449.1.1.8.5.5.1
-- 1.3.6.1.4.1.25449.1.1.8.5.5.1
		-- 1.3.6.1.4.1.25449.1.1.8.5.5.1
		eciIfMdVCGPerformanceEntry OBJECT-TYPE
			SYNTAX EciIfMdVCGPerformanceEntry
			MAX-ACCESS not-accessible
			STATUS current
			DESCRIPTION
				"VCG channel table entry"
			INDEX { eciESDeviceIndex, eciIfMdVCGChannelIndex }
			::= { eciIfMdVCGPerformanceTable 1 }

		
		EciIfMdVCGPerformanceEntry ::=
			SEQUENCE { 
				eciIfMdVCGPerformanceTx
					INTEGER,
				eciIfMdVCGPerformanceRx
					INTEGER
			 }

--    1.3.6.1.4.1.25449.1.1.8.5.5.1.1
-- 1.3.6.1.4.1.25449.1.1.8.5.5.1.1
-- 1.3.6.1.4.1.25449.1.1.8.5.5.1.1
		-- 1.3.6.1.4.1.25449.1.1.8.5.5.1.1
		eciIfMdVCGPerformanceTx OBJECT-TYPE
			SYNTAX INTEGER
			MAX-ACCESS read-only
			STATUS current
			DESCRIPTION
				" "
			::= { eciIfMdVCGPerformanceEntry 1 }

		
--    1.3.6.1.4.1.25449.1.1.8.5.5.1.2
-- 1.3.6.1.4.1.25449.1.1.8.5.5.1.2
-- 1.3.6.1.4.1.25449.1.1.8.5.5.1.2
		-- 1.3.6.1.4.1.25449.1.1.8.5.5.1.2
		eciIfMdVCGPerformanceRx OBJECT-TYPE
			SYNTAX INTEGER
			MAX-ACCESS read-only
			STATUS current
			DESCRIPTION
				" "
			::= { eciIfMdVCGPerformanceEntry 2 }

		
--    1.3.6.1.4.1.25449.1.1.8.5.6
-- 1.3.6.1.4.1.25449.1.1.8.5.6
-- 1.3.6.1.4.1.25449.1.1.8.5.6
		-- 1.3.6.1.4.1.25449.1.1.8.5.6
		eciIfMdVCGOperation OBJECT IDENTIFIER ::= { eciIfMdVCG 6 }

		
--    1.3.6.1.4.1.25449.1.1.8.5.6.1
-- 1.3.6.1.4.1.25449.1.1.8.5.6.1
-- 1.3.6.1.4.1.25449.1.1.8.5.6.1
		-- 1.3.6.1.4.1.25449.1.1.8.5.6.1
		eciIfMdVCGOperationTable OBJECT-TYPE
			SYNTAX SEQUENCE OF EciIfMdVCGOperationEntry
			MAX-ACCESS not-accessible
			STATUS current
			DESCRIPTION
				" "
			::= { eciIfMdVCGOperation 1 }

		
--    1.3.6.1.4.1.25449.1.1.8.5.6.1.1
-- 1.3.6.1.4.1.25449.1.1.8.5.6.1.1
-- 1.3.6.1.4.1.25449.1.1.8.5.6.1.1
		-- 1.3.6.1.4.1.25449.1.1.8.5.6.1.1
		eciIfMdVCGOperationEntry OBJECT-TYPE
			SYNTAX EciIfMdVCGOperationEntry
			MAX-ACCESS not-accessible
			STATUS current
			DESCRIPTION
				" "
			INDEX { eciESDeviceIndex }
			::= { eciIfMdVCGOperationTable 1 }

		
		EciIfMdVCGOperationEntry ::=
			SEQUENCE { 
				eciIfMdOperationVCGNew
					OCTET STRING,
				eciIfMdOperationVCGDelete
					INTEGER,
				eciIfMdOperationVCGRepair
					DisplayString,
				eciIfMdOperationVCGActive
					INTEGER
			 }

--    1.3.6.1.4.1.25449.1.1.8.5.6.1.1.1
-- 1.3.6.1.4.1.25449.1.1.8.5.6.1.1.1
-- 1.3.6.1.4.1.25449.1.1.8.5.6.1.1.1
		-- 1.3.6.1.4.1.25449.1.1.8.5.6.1.1.1
		eciIfMdOperationVCGNew OBJECT-TYPE
			SYNTAX OCTET STRING
			MAX-ACCESS read-write
			STATUS current
			DESCRIPTION
				" "
			::= { eciIfMdVCGOperationEntry 1 }

		
--    1.3.6.1.4.1.25449.1.1.8.5.6.1.1.2
-- 1.3.6.1.4.1.25449.1.1.8.5.6.1.1.2
-- 1.3.6.1.4.1.25449.1.1.8.5.6.1.1.2
		-- 1.3.6.1.4.1.25449.1.1.8.5.6.1.1.2
		eciIfMdOperationVCGDelete OBJECT-TYPE
			SYNTAX INTEGER
			MAX-ACCESS read-write
			STATUS current
			DESCRIPTION
				" "
			::= { eciIfMdVCGOperationEntry 2 }

		
--    1.3.6.1.4.1.25449.1.1.8.5.6.1.1.3
-- 1.3.6.1.4.1.25449.1.1.8.5.6.1.1.3
-- 1.3.6.1.4.1.25449.1.1.8.5.6.1.1.3
		-- 1.3.6.1.4.1.25449.1.1.8.5.6.1.1.3
		eciIfMdOperationVCGRepair OBJECT-TYPE
			SYNTAX DisplayString
			MAX-ACCESS read-write
			STATUS current
			DESCRIPTION
				" "
			::= { eciIfMdVCGOperationEntry 3 }

		
--    1.3.6.1.4.1.25449.1.1.8.5.6.1.1.4
-- 1.3.6.1.4.1.25449.1.1.8.5.6.1.1.4
-- 1.3.6.1.4.1.25449.1.1.8.5.6.1.1.4
		-- 1.3.6.1.4.1.25449.1.1.8.5.6.1.1.4
		eciIfMdOperationVCGActive OBJECT-TYPE
			SYNTAX INTEGER
			MAX-ACCESS read-write
			STATUS current
			DESCRIPTION
				" "
			::= { eciIfMdVCGOperationEntry 4 }

		
--    1.3.6.1.4.1.25449.1.1.8.5.6.5
-- 1.3.6.1.4.1.25449.1.1.8.5.6.5
-- 1.3.6.1.4.1.25449.1.1.8.5.6.5
		-- 1.3.6.1.4.1.25449.1.1.8.5.6.5
		eciIfMdVirtualVCGAttributeTable OBJECT-TYPE
			SYNTAX SEQUENCE OF EciIfMdVirtualVCGAttributeEntry
			MAX-ACCESS not-accessible
			STATUS current
			DESCRIPTION
				" "
			::= { eciIfMdVCGOperation 5 }

		
--    1.3.6.1.4.1.25449.1.1.8.5.6.5.1
-- 1.3.6.1.4.1.25449.1.1.8.5.6.5.1
-- 1.3.6.1.4.1.25449.1.1.8.5.6.5.1
		-- 1.3.6.1.4.1.25449.1.1.8.5.6.5.1
		eciIfMdVirtualVCGAttributeEntry OBJECT-TYPE
			SYNTAX EciIfMdVirtualVCGAttributeEntry
			MAX-ACCESS not-accessible
			STATUS current
			DESCRIPTION
				" "
			INDEX { eciESDeviceIndex, eciIfMdVirtualVCGChannelIndex }
			::= { eciIfMdVirtualVCGAttributeTable 1 }

		
		EciIfMdVirtualVCGAttributeEntry ::=
			SEQUENCE { 
				eciIfMdVirtualVCGChannelIndex
					INTEGER,
				eciIfMdVirtualOperationPFCSConfig
					INTEGER,
				eciIfMdVirtualOperationVCGName
					DisplayString,
				eciIfMdVirtualOperationIfNMChannel
					INTEGER,
				eciIfMdVirtualOperationState
					INTEGER
			 }

--    1.3.6.1.4.1.25449.1.1.8.5.6.5.1.1
-- 1.3.6.1.4.1.25449.1.1.8.5.6.5.1.1
-- 1.3.6.1.4.1.25449.1.1.8.5.6.5.1.1
		-- 1.3.6.1.4.1.25449.1.1.8.5.6.5.1.1
		eciIfMdVirtualVCGChannelIndex OBJECT-TYPE
			SYNTAX INTEGER
			MAX-ACCESS read-only
			STATUS current
			DESCRIPTION
				" "
			::= { eciIfMdVirtualVCGAttributeEntry 1 }

		
--    1.3.6.1.4.1.25449.1.1.8.5.6.5.1.2
-- 1.3.6.1.4.1.25449.1.1.8.5.6.5.1.2
-- 1.3.6.1.4.1.25449.1.1.8.5.6.5.1.2
		-- 1.3.6.1.4.1.25449.1.1.8.5.6.5.1.2
		eciIfMdVirtualOperationPFCSConfig OBJECT-TYPE
			SYNTAX INTEGER
			MAX-ACCESS read-write
			STATUS current
			DESCRIPTION
				" "
			::= { eciIfMdVirtualVCGAttributeEntry 2 }

		
--    1.3.6.1.4.1.25449.1.1.8.5.6.5.1.3
-- 1.3.6.1.4.1.25449.1.1.8.5.6.5.1.3
-- 1.3.6.1.4.1.25449.1.1.8.5.6.5.1.3
		-- 1.3.6.1.4.1.25449.1.1.8.5.6.5.1.3
		eciIfMdVirtualOperationVCGName OBJECT-TYPE
			SYNTAX DisplayString
			MAX-ACCESS read-write
			STATUS current
			DESCRIPTION
				" "
			::= { eciIfMdVirtualVCGAttributeEntry 3 }

		
--    1.3.6.1.4.1.25449.1.1.8.5.6.5.1.4
-- 1.3.6.1.4.1.25449.1.1.8.5.6.5.1.4
-- 1.3.6.1.4.1.25449.1.1.8.5.6.5.1.4
		-- 1.3.6.1.4.1.25449.1.1.8.5.6.5.1.4
		eciIfMdVirtualOperationIfNMChannel OBJECT-TYPE
			SYNTAX INTEGER
				{
				normal(0),
				nmPort(1)
				}
			MAX-ACCESS read-only
			STATUS current
			DESCRIPTION
				" "
			::= { eciIfMdVirtualVCGAttributeEntry 4 }

		
--    1.3.6.1.4.1.25449.1.1.8.5.6.5.1.5
-- 1.3.6.1.4.1.25449.1.1.8.5.6.5.1.5
-- 1.3.6.1.4.1.25449.1.1.8.5.6.5.1.5
		-- 1.3.6.1.4.1.25449.1.1.8.5.6.5.1.5
		eciIfMdVirtualOperationState OBJECT-TYPE
			SYNTAX INTEGER
			MAX-ACCESS read-only
			STATUS current
			DESCRIPTION
				" "
			::= { eciIfMdVirtualVCGAttributeEntry 5 }

		
--    1.3.6.1.4.1.25449.1.1.8.5.6.6
-- 1.3.6.1.4.1.25449.1.1.8.5.6.6
-- 1.3.6.1.4.1.25449.1.1.8.5.6.6
		-- 1.3.6.1.4.1.25449.1.1.8.5.6.6
		eciIfMdVirtualVCGMemberTable OBJECT-TYPE
			SYNTAX SEQUENCE OF EciIfMdVirtualVCGMemberEntry
			MAX-ACCESS not-accessible
			STATUS current
			DESCRIPTION
				" "
			::= { eciIfMdVCGOperation 6 }

		
--    1.3.6.1.4.1.25449.1.1.8.5.6.6.1
-- 1.3.6.1.4.1.25449.1.1.8.5.6.6.1
-- 1.3.6.1.4.1.25449.1.1.8.5.6.6.1
		-- 1.3.6.1.4.1.25449.1.1.8.5.6.6.1
		eciIfMdVirtualVCGMemberEntry OBJECT-TYPE
			SYNTAX EciIfMdVirtualVCGMemberEntry
			MAX-ACCESS not-accessible
			STATUS current
			DESCRIPTION
				" "
			INDEX { eciESDeviceIndex, eciIfMdVirtualVCGChannelIndex, eciIfMdVirtualVCGMemberSerialN }
			::= { eciIfMdVirtualVCGMemberTable 1 }

		
		EciIfMdVirtualVCGMemberEntry ::=
			SEQUENCE { 
				eciIfMdVirtualVCGMemberSerialN
					INTEGER,
				eciIfMdOperationCHVCIndex
					INTEGER,
				eciIfMdOperationVC12Index
					INTEGER,
				eciIfMdOperationSNCPConfig
					INTEGER
			 }

--    1.3.6.1.4.1.25449.1.1.8.5.6.6.1.1
-- 1.3.6.1.4.1.25449.1.1.8.5.6.6.1.1
-- 1.3.6.1.4.1.25449.1.1.8.5.6.6.1.1
		-- 1.3.6.1.4.1.25449.1.1.8.5.6.6.1.1
		eciIfMdVirtualVCGMemberSerialN OBJECT-TYPE
			SYNTAX INTEGER (1..16)
			MAX-ACCESS read-only
			STATUS current
			DESCRIPTION
				" "
			::= { eciIfMdVirtualVCGMemberEntry 1 }

		
--    1.3.6.1.4.1.25449.1.1.8.5.6.6.1.2
-- 1.3.6.1.4.1.25449.1.1.8.5.6.6.1.2
-- 1.3.6.1.4.1.25449.1.1.8.5.6.6.1.2
		-- 1.3.6.1.4.1.25449.1.1.8.5.6.6.1.2
		eciIfMdOperationCHVCIndex OBJECT-TYPE
			SYNTAX INTEGER
			MAX-ACCESS read-only
			STATUS current
			DESCRIPTION
				" "
			::= { eciIfMdVirtualVCGMemberEntry 2 }

		
--    1.3.6.1.4.1.25449.1.1.8.5.6.6.1.3
-- 1.3.6.1.4.1.25449.1.1.8.5.6.6.1.3
-- 1.3.6.1.4.1.25449.1.1.8.5.6.6.1.3
		-- 1.3.6.1.4.1.25449.1.1.8.5.6.6.1.3
		eciIfMdOperationVC12Index OBJECT-TYPE
			SYNTAX INTEGER
			MAX-ACCESS read-write
			STATUS current
			DESCRIPTION
				" "
			::= { eciIfMdVirtualVCGMemberEntry 3 }

		
--    1.3.6.1.4.1.25449.1.1.8.5.6.6.1.4
-- 1.3.6.1.4.1.25449.1.1.8.5.6.6.1.4
-- 1.3.6.1.4.1.25449.1.1.8.5.6.6.1.4
		-- 1.3.6.1.4.1.25449.1.1.8.5.6.6.1.4
		eciIfMdOperationSNCPConfig OBJECT-TYPE
			SYNTAX INTEGER
				{
				disable(0),
				enable(1)
				}
			MAX-ACCESS read-write
			STATUS current
			DESCRIPTION
				" "
			::= { eciIfMdVirtualVCGMemberEntry 4 }

		
--    1.3.6.1.4.1.25449.1.1.8.5.6.7
-- 1.3.6.1.4.1.25449.1.1.8.5.6.7
-- 1.3.6.1.4.1.25449.1.1.8.5.6.7
		-- 1.3.6.1.4.1.25449.1.1.8.5.6.7
		eciIfMdVirtualVCGVLANIDTable OBJECT-TYPE
			SYNTAX SEQUENCE OF EciIfMdVirtualVCGVLANIDEntry
			MAX-ACCESS not-accessible
			STATUS current
			DESCRIPTION
				" "
			::= { eciIfMdVCGOperation 7 }

		
--    1.3.6.1.4.1.25449.1.1.8.5.6.7.1
-- 1.3.6.1.4.1.25449.1.1.8.5.6.7.1
-- 1.3.6.1.4.1.25449.1.1.8.5.6.7.1
		-- 1.3.6.1.4.1.25449.1.1.8.5.6.7.1
		eciIfMdVirtualVCGVLANIDEntry OBJECT-TYPE
			SYNTAX EciIfMdVirtualVCGVLANIDEntry
			MAX-ACCESS not-accessible
			STATUS current
			DESCRIPTION
				" "
			INDEX { eciESDeviceIndex, eciIfMdVirtualVCGChannelIndex, eciIfMdVirtualVCGVLANIDSerialN }
			::= { eciIfMdVirtualVCGVLANIDTable 1 }

		
		EciIfMdVirtualVCGVLANIDEntry ::=
			SEQUENCE { 
				eciIfMdVirtualVCGVLANIDSerialN
					INTEGER,
				eciIfMdVirtualVCGVLANID
					INTEGER
			 }

--    1.3.6.1.4.1.25449.1.1.8.5.6.7.1.1
-- 1.3.6.1.4.1.25449.1.1.8.5.6.7.1.1
-- 1.3.6.1.4.1.25449.1.1.8.5.6.7.1.1
		-- 1.3.6.1.4.1.25449.1.1.8.5.6.7.1.1
		eciIfMdVirtualVCGVLANIDSerialN OBJECT-TYPE
			SYNTAX INTEGER
			MAX-ACCESS read-only
			STATUS current
			DESCRIPTION
				" "
			::= { eciIfMdVirtualVCGVLANIDEntry 1 }

		
--    1.3.6.1.4.1.25449.1.1.8.5.6.7.1.2
-- 1.3.6.1.4.1.25449.1.1.8.5.6.7.1.2
-- 1.3.6.1.4.1.25449.1.1.8.5.6.7.1.2
		-- 1.3.6.1.4.1.25449.1.1.8.5.6.7.1.2
		eciIfMdVirtualVCGVLANID OBJECT-TYPE
			SYNTAX INTEGER
			MAX-ACCESS read-write
			STATUS current
			DESCRIPTION
				" "
			::= { eciIfMdVirtualVCGVLANIDEntry 2 }

		
--    1.3.6.1.4.1.25449.1.1.8.5.9
-- 1.3.6.1.4.1.25449.1.1.8.5.9
-- 1.3.6.1.4.1.25449.1.1.8.5.9
		-- 1.3.6.1.4.1.25449.1.1.8.5.9
		eciIfMdVCGVLANIDTable OBJECT-TYPE
			SYNTAX SEQUENCE OF EciIfMdVCGVLANIDEntry
			MAX-ACCESS not-accessible
			STATUS current
			DESCRIPTION
				" "
			::= { eciIfMdVCG 9 }

		
--    1.3.6.1.4.1.25449.1.1.8.5.9.1
-- 1.3.6.1.4.1.25449.1.1.8.5.9.1
-- 1.3.6.1.4.1.25449.1.1.8.5.9.1
		-- 1.3.6.1.4.1.25449.1.1.8.5.9.1
		eciIfMdVCGVLANIDEntry OBJECT-TYPE
			SYNTAX EciIfMdVCGVLANIDEntry
			MAX-ACCESS not-accessible
			STATUS current
			DESCRIPTION
				" "
			INDEX { eciESDeviceIndex, eciIfMdVCGChannelIndex, eciIfMdVCGVLANIDSerialN }
			::= { eciIfMdVCGVLANIDTable 1 }

		
		EciIfMdVCGVLANIDEntry ::=
			SEQUENCE { 
				eciIfMdVCGVLANIDSerialN
					INTEGER,
				eciIfMdVCGVLANID
					INTEGER
			 }

--    1.3.6.1.4.1.25449.1.1.8.5.9.1.1
-- 1.3.6.1.4.1.25449.1.1.8.5.9.1.1
-- 1.3.6.1.4.1.25449.1.1.8.5.9.1.1
		-- 1.3.6.1.4.1.25449.1.1.8.5.9.1.1
		eciIfMdVCGVLANIDSerialN OBJECT-TYPE
			SYNTAX INTEGER
			MAX-ACCESS read-only
			STATUS current
			DESCRIPTION
				" "
			::= { eciIfMdVCGVLANIDEntry 1 }

		
--    1.3.6.1.4.1.25449.1.1.8.5.9.1.2
-- 1.3.6.1.4.1.25449.1.1.8.5.9.1.2
-- 1.3.6.1.4.1.25449.1.1.8.5.9.1.2
		-- 1.3.6.1.4.1.25449.1.1.8.5.9.1.2
		eciIfMdVCGVLANID OBJECT-TYPE
			SYNTAX INTEGER
			MAX-ACCESS read-only
			STATUS current
			DESCRIPTION
				" "
			::= { eciIfMdVCGVLANIDEntry 2 }

		
--    1.3.6.1.4.1.25449.1.1.8.5.10
-- 1.3.6.1.4.1.25449.1.1.8.5.10
-- 1.3.6.1.4.1.25449.1.1.8.5.10
		-- 1.3.6.1.4.1.25449.1.1.8.5.10
		eciIfMdVCGMemberTable OBJECT-TYPE
			SYNTAX SEQUENCE OF EciIfMdVCGMemberEntry
			MAX-ACCESS not-accessible
			STATUS current
			DESCRIPTION
				" "
			::= { eciIfMdVCG 10 }

		
--    1.3.6.1.4.1.25449.1.1.8.5.10.1
-- 1.3.6.1.4.1.25449.1.1.8.5.10.1
-- 1.3.6.1.4.1.25449.1.1.8.5.10.1
		-- 1.3.6.1.4.1.25449.1.1.8.5.10.1
		eciIfMdVCGMemberEntry OBJECT-TYPE
			SYNTAX EciIfMdVCGMemberEntry
			MAX-ACCESS not-accessible
			STATUS current
			DESCRIPTION
				" "
			INDEX { eciESDeviceIndex, eciIfMdVCGChannelIndex, eciIfMdVCGMemberSerialN }
			::= { eciIfMdVCGMemberTable 1 }

		
		EciIfMdVCGMemberEntry ::=
			SEQUENCE { 
				eciIfMdVCGMemberSerialN
					INTEGER,
				eciIfMdMemberCHVCIndex
					INTEGER,
				eciIfMdMemberVC12Index
					INTEGER,
				eciIfMdMemberSNCPConfig
					INTEGER
			 }

--    1.3.6.1.4.1.25449.1.1.8.5.10.1.1
-- 1.3.6.1.4.1.25449.1.1.8.5.10.1.1
-- 1.3.6.1.4.1.25449.1.1.8.5.10.1.1
		-- 1.3.6.1.4.1.25449.1.1.8.5.10.1.1
		eciIfMdVCGMemberSerialN OBJECT-TYPE
			SYNTAX INTEGER
			MAX-ACCESS read-only
			STATUS current
			DESCRIPTION
				" "
			::= { eciIfMdVCGMemberEntry 1 }

		
--    1.3.6.1.4.1.25449.1.1.8.5.10.1.2
-- 1.3.6.1.4.1.25449.1.1.8.5.10.1.2
-- 1.3.6.1.4.1.25449.1.1.8.5.10.1.2
		-- 1.3.6.1.4.1.25449.1.1.8.5.10.1.2
		eciIfMdMemberCHVCIndex OBJECT-TYPE
			SYNTAX INTEGER
			MAX-ACCESS read-only
			STATUS current
			DESCRIPTION
				" "
			::= { eciIfMdVCGMemberEntry 2 }

		
--    1.3.6.1.4.1.25449.1.1.8.5.10.1.3
-- 1.3.6.1.4.1.25449.1.1.8.5.10.1.3
-- 1.3.6.1.4.1.25449.1.1.8.5.10.1.3
		-- 1.3.6.1.4.1.25449.1.1.8.5.10.1.3
		eciIfMdMemberVC12Index OBJECT-TYPE
			SYNTAX INTEGER
			MAX-ACCESS read-only
			STATUS current
			DESCRIPTION
				" "
			::= { eciIfMdVCGMemberEntry 3 }

		
--    1.3.6.1.4.1.25449.1.1.8.5.10.1.4
-- 1.3.6.1.4.1.25449.1.1.8.5.10.1.4
-- 1.3.6.1.4.1.25449.1.1.8.5.10.1.4
		-- 1.3.6.1.4.1.25449.1.1.8.5.10.1.4
		eciIfMdMemberSNCPConfig OBJECT-TYPE
			SYNTAX INTEGER
			MAX-ACCESS read-only
			STATUS current
			DESCRIPTION
				" "
			::= { eciIfMdVCGMemberEntry 4 }

		
--    1.3.6.1.4.1.25449.1.1.8.5.12
-- 1.3.6.1.4.1.25449.1.1.8.5.12
-- 1.3.6.1.4.1.25449.1.1.8.5.12
		-- 1.3.6.1.4.1.25449.1.1.8.5.12
		eciIfMdVCGSwitchModeTable OBJECT-TYPE
			SYNTAX SEQUENCE OF EciIfMdVCGSwitchModeEntry
			MAX-ACCESS not-accessible
			STATUS current
			DESCRIPTION
				" "
			::= { eciIfMdVCG 12 }

		
--    1.3.6.1.4.1.25449.1.1.8.5.12.1
-- 1.3.6.1.4.1.25449.1.1.8.5.12.1
-- 1.3.6.1.4.1.25449.1.1.8.5.12.1
		-- 1.3.6.1.4.1.25449.1.1.8.5.12.1
		eciIfMdVCGSwitchModeEntry OBJECT-TYPE
			SYNTAX EciIfMdVCGSwitchModeEntry
			MAX-ACCESS not-accessible
			STATUS current
			DESCRIPTION
				" "
			INDEX { eciESDeviceIndex }
			::= { eciIfMdVCGSwitchModeTable 1 }

		
		EciIfMdVCGSwitchModeEntry ::=
			SEQUENCE { 
				eciIfMdVCGSwitchMode
					INTEGER
			 }

--    1.3.6.1.4.1.25449.1.1.8.5.12.1.1
-- 1.3.6.1.4.1.25449.1.1.8.5.12.1.1
-- 1.3.6.1.4.1.25449.1.1.8.5.12.1.1
		-- 1.3.6.1.4.1.25449.1.1.8.5.12.1.1
		eciIfMdVCGSwitchMode OBJECT-TYPE
			SYNTAX INTEGER
				{
				fullswitch(1),
				aggregation(2),
				i8021q(3)
				}
			MAX-ACCESS read-write
			STATUS current
			DESCRIPTION
				" "
			::= { eciIfMdVCGSwitchModeEntry 1 }

		
--    1.3.6.1.4.1.25449.1.1.8.5.13
-- 1.3.6.1.4.1.25449.1.1.8.5.13
-- 1.3.6.1.4.1.25449.1.1.8.5.13
		-- 1.3.6.1.4.1.25449.1.1.8.5.13
		eciIfMdVCGStatusCounterTable OBJECT-TYPE
			SYNTAX SEQUENCE OF EciIfMdVCGStatusCounterEntry
			MAX-ACCESS not-accessible
			STATUS current
			DESCRIPTION
				" "
			::= { eciIfMdVCG 13 }

		
--    1.3.6.1.4.1.25449.1.1.8.5.13.1
-- 1.3.6.1.4.1.25449.1.1.8.5.13.1
-- 1.3.6.1.4.1.25449.1.1.8.5.13.1
		-- 1.3.6.1.4.1.25449.1.1.8.5.13.1
		eciIfMdVCGStatusCounterEntry OBJECT-TYPE
			SYNTAX EciIfMdVCGStatusCounterEntry
			MAX-ACCESS not-accessible
			STATUS current
			DESCRIPTION
				" "
			INDEX { eciESDeviceIndex, eciIfMdVCGChannelIndex }
			::= { eciIfMdVCGStatusCounterTable 1 }

		
		EciIfMdVCGStatusCounterEntry ::=
			SEQUENCE { 
				eciIfMdVCGSyncStatus
					INTEGER,
				eciIfMdVCGCounterUpPackage
					INTEGER,
				eciIfMdVCGCounterDownPackage
					INTEGER,
				eciIfMdVCGCounterPfcsErrorPackage
					INTEGER,
				eciIfMdVCGCounterHunt
					INTEGER,
				eciIfMdVCGValidMemberNumber
					INTEGER,
				eciIfMdVCGConfigMemberNumber
					INTEGER,
				eciIfMdVCGStChannelName
					DisplayString,
				eciIfMdVCGCounterReset
					INTEGER
			 }

--    1.3.6.1.4.1.25449.1.1.8.5.13.1.1
-- 1.3.6.1.4.1.25449.1.1.8.5.13.1.1
-- 1.3.6.1.4.1.25449.1.1.8.5.13.1.1
		-- 1.3.6.1.4.1.25449.1.1.8.5.13.1.1
		eciIfMdVCGSyncStatus OBJECT-TYPE
			SYNTAX INTEGER
				{
				loss(0),
				synchronous(1)
				}
			MAX-ACCESS read-only
			STATUS current
			DESCRIPTION
				" "
			::= { eciIfMdVCGStatusCounterEntry 1 }

		
--    1.3.6.1.4.1.25449.1.1.8.5.13.1.2
-- 1.3.6.1.4.1.25449.1.1.8.5.13.1.2
-- 1.3.6.1.4.1.25449.1.1.8.5.13.1.2
		-- 1.3.6.1.4.1.25449.1.1.8.5.13.1.2
		eciIfMdVCGCounterUpPackage OBJECT-TYPE
			SYNTAX INTEGER
			MAX-ACCESS read-only
			STATUS current
			DESCRIPTION
				" "
			::= { eciIfMdVCGStatusCounterEntry 2 }

		
--    1.3.6.1.4.1.25449.1.1.8.5.13.1.3
-- 1.3.6.1.4.1.25449.1.1.8.5.13.1.3
-- 1.3.6.1.4.1.25449.1.1.8.5.13.1.3
		-- 1.3.6.1.4.1.25449.1.1.8.5.13.1.3
		eciIfMdVCGCounterDownPackage OBJECT-TYPE
			SYNTAX INTEGER
			MAX-ACCESS read-only
			STATUS current
			DESCRIPTION
				" "
			::= { eciIfMdVCGStatusCounterEntry 3 }

		
--    1.3.6.1.4.1.25449.1.1.8.5.13.1.4
-- 1.3.6.1.4.1.25449.1.1.8.5.13.1.4
-- 1.3.6.1.4.1.25449.1.1.8.5.13.1.4
		-- 1.3.6.1.4.1.25449.1.1.8.5.13.1.4
		eciIfMdVCGCounterPfcsErrorPackage OBJECT-TYPE
			SYNTAX INTEGER
			MAX-ACCESS read-only
			STATUS current
			DESCRIPTION
				" "
			::= { eciIfMdVCGStatusCounterEntry 4 }

		
--    1.3.6.1.4.1.25449.1.1.8.5.13.1.5
-- 1.3.6.1.4.1.25449.1.1.8.5.13.1.5
-- 1.3.6.1.4.1.25449.1.1.8.5.13.1.5
		-- 1.3.6.1.4.1.25449.1.1.8.5.13.1.5
		eciIfMdVCGCounterHunt OBJECT-TYPE
			SYNTAX INTEGER
			MAX-ACCESS read-only
			STATUS current
			DESCRIPTION
				" "
			::= { eciIfMdVCGStatusCounterEntry 5 }

		
--    1.3.6.1.4.1.25449.1.1.8.5.13.1.6
-- 1.3.6.1.4.1.25449.1.1.8.5.13.1.6
-- 1.3.6.1.4.1.25449.1.1.8.5.13.1.6
		-- 1.3.6.1.4.1.25449.1.1.8.5.13.1.6
		eciIfMdVCGValidMemberNumber OBJECT-TYPE
			SYNTAX INTEGER
			MAX-ACCESS read-only
			STATUS current
			DESCRIPTION
				" "
			::= { eciIfMdVCGStatusCounterEntry 6 }

		
--    1.3.6.1.4.1.25449.1.1.8.5.13.1.7
-- 1.3.6.1.4.1.25449.1.1.8.5.13.1.7
-- 1.3.6.1.4.1.25449.1.1.8.5.13.1.7
		-- 1.3.6.1.4.1.25449.1.1.8.5.13.1.7
		eciIfMdVCGConfigMemberNumber OBJECT-TYPE
			SYNTAX INTEGER
			MAX-ACCESS read-only
			STATUS current
			DESCRIPTION
				" "
			::= { eciIfMdVCGStatusCounterEntry 7 }

		
--    1.3.6.1.4.1.25449.1.1.8.5.13.1.8
-- 1.3.6.1.4.1.25449.1.1.8.5.13.1.8
-- 1.3.6.1.4.1.25449.1.1.8.5.13.1.8
		-- 1.3.6.1.4.1.25449.1.1.8.5.13.1.8
		eciIfMdVCGStChannelName OBJECT-TYPE
			SYNTAX DisplayString
			MAX-ACCESS read-only
			STATUS current
			DESCRIPTION
				" "
			::= { eciIfMdVCGStatusCounterEntry 8 }

		
--    1.3.6.1.4.1.25449.1.1.8.5.13.1.9
-- 1.3.6.1.4.1.25449.1.1.8.5.13.1.9
-- 1.3.6.1.4.1.25449.1.1.8.5.13.1.9
		-- 1.3.6.1.4.1.25449.1.1.8.5.13.1.9
		eciIfMdVCGCounterReset OBJECT-TYPE
			SYNTAX INTEGER
			MAX-ACCESS read-write
			STATUS current
			DESCRIPTION
				" "
			::= { eciIfMdVCGStatusCounterEntry 9 }

		
	
	END

--
-- EZWELL-IFVCG-MIB.mib
--
