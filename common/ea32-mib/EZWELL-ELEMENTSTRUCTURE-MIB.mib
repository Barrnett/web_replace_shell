--
-- EZWELL-ELEMENTSTRUCTURE-MIB.mib
-- MIB generated by MG-SOFT Visual MIB Builder Version 6.0  Build 88
-- Friday, September 11, 2015 at 15:25:56
--

--  EZWELL-ELEMENTSTRUCTURE-MIB.mib
-- MIB generated by MG-SOFT Visual MIB Builder Version 6.0  Build 88
-- Thursday, September 10, 2015 at 10:37:41
-- 
--  Easy BroadBand Technology MIB VER 2.0 (date 2009.10.1)
-- 
-- Easy BroadBand Technology specific MIB for element structure property.
-- dated  2009.10.1
-- Version 2.0 

	EZWELL-ELEMENTSTRUCTURE-MIB DEFINITIONS ::= BEGIN
 
		IMPORTS
			eciElementStructure			
				FROM EZWELL-GENERAL-MODEL-MIB			
			DisplayString			
				FROM RFC1213-MIB			
			OBJECT-TYPE			
				FROM SNMPv2-SMI;
	
	
	
--
-- Node definitions
--
	
--  Node definitions
-- 
-- device list entry         
-- 1.3.6.1.4.1.25449.1.1.3.1
		-- 1.3.6.1.4.1.25449.1.1.3.1
		eciESDevice OBJECT IDENTIFIER ::= { eciElementStructure 1 }

		
--  1.3.6.1.4.1.25449.1.1.3.1.1
		-- 1.3.6.1.4.1.25449.1.1.3.1.1
		eciESDeviceNumber OBJECT-TYPE
			SYNTAX INTEGER
			MAX-ACCESS read-only
			STATUS current
			DESCRIPTION
				"numbers of devices which included by a element"
			::= { eciESDevice 1 }

		
--  1.3.6.1.4.1.25449.1.1.3.1.2
		-- 1.3.6.1.4.1.25449.1.1.3.1.2
		eciESDeviceTable OBJECT-TYPE
			SYNTAX SEQUENCE OF EciESDeviceEntry
			MAX-ACCESS not-accessible
			STATUS current
			DESCRIPTION
				"devices list table"
			::= { eciESDevice 2 }

		
--  1.3.6.1.4.1.25449.1.1.3.1.2.1
		-- 1.3.6.1.4.1.25449.1.1.3.1.2.1
		eciESDeviceEntry OBJECT-TYPE
			SYNTAX EciESDeviceEntry
			MAX-ACCESS not-accessible
			STATUS current
			DESCRIPTION
				"devices list table entry"
			INDEX { eciESDeviceIndex }
			::= { eciESDeviceTable 1 }

		
		EciESDeviceEntry ::=
			SEQUENCE { 
				eciESDeviceIndex
					INTEGER,
				eciESDeviceTypeName
					DisplayString,
				eciESDeviceType
					INTEGER,
				eciESDeviceName
					DisplayString,
				eciESDeviceStatus
					INTEGER,
				eciESDeviceLocation
					INTEGER,
				eciESDeviceIsChassis
					INTEGER,
				eciESDeviceSlotNumber
					INTEGER,
				eciESDeviceCommand
					DisplayString,
				eciESDeviceLoadCommand
					DisplayString,
				eciESDeviceLightStatus
					OCTET STRING
			 }

--  1.3.6.1.4.1.25449.1.1.3.1.2.1.1
		-- 1.3.6.1.4.1.25449.1.1.3.1.2.1.1
		eciESDeviceIndex OBJECT-TYPE
			SYNTAX INTEGER
			MAX-ACCESS read-only
			STATUS current
			DESCRIPTION
				"devices unique index"
			::= { eciESDeviceEntry 1 }

		
--  1.3.6.1.4.1.25449.1.1.3.1.2.1.2
		-- 1.3.6.1.4.1.25449.1.1.3.1.2.1.2
		eciESDeviceTypeName OBJECT-TYPE
			SYNTAX DisplayString (SIZE (0..31))
			MAX-ACCESS read-only
			STATUS current
			DESCRIPTION
				"device unique type name"
			::= { eciESDeviceEntry 2 }

		
--  1.3.6.1.4.1.25449.1.1.3.1.2.1.3
		-- 1.3.6.1.4.1.25449.1.1.3.1.2.1.3
		eciESDeviceType OBJECT-TYPE
			SYNTAX INTEGER
			MAX-ACCESS read-only
			STATUS current
			DESCRIPTION
				"device unique type ID"
			::= { eciESDeviceEntry 3 }

		
--  1.3.6.1.4.1.25449.1.1.3.1.2.1.4
		-- 1.3.6.1.4.1.25449.1.1.3.1.2.1.4
		eciESDeviceName OBJECT-TYPE
			SYNTAX DisplayString (SIZE (0..31))
			MAX-ACCESS read-only
			STATUS current
			DESCRIPTION
				"device description"
			::= { eciESDeviceEntry 4 }

		
--  1.3.6.1.4.1.25449.1.1.3.1.2.1.5
		-- 1.3.6.1.4.1.25449.1.1.3.1.2.1.5
		eciESDeviceStatus OBJECT-TYPE
			SYNTAX INTEGER
				{
				normal(1),
				fault(0)
				}
			MAX-ACCESS read-only
			STATUS current
			DESCRIPTION
				"device status.
				fault is device run in fault.
				linkdown is device lost connection."
			::= { eciESDeviceEntry 5 }

		
--  1.3.6.1.4.1.25449.1.1.3.1.2.1.6
		-- 1.3.6.1.4.1.25449.1.1.3.1.2.1.6
		eciESDeviceLocation OBJECT-TYPE
			SYNTAX INTEGER
				{
				local(1),
				remote(2)
				}
			MAX-ACCESS read-only
			STATUS current
			DESCRIPTION
				"local device or remote device or third device"
			::= { eciESDeviceEntry 6 }

		
--  1.3.6.1.4.1.25449.1.1.3.1.2.1.7
		-- 1.3.6.1.4.1.25449.1.1.3.1.2.1.7
		eciESDeviceIsChassis OBJECT-TYPE
			SYNTAX INTEGER
				{
				chassis(1),
				single(2)
				}
			MAX-ACCESS read-only
			STATUS current
			DESCRIPTION
				"chassis flag"
			::= { eciESDeviceEntry 7 }

		
--  1.3.6.1.4.1.25449.1.1.3.1.2.1.8
		-- 1.3.6.1.4.1.25449.1.1.3.1.2.1.8
		eciESDeviceSlotNumber OBJECT-TYPE
			SYNTAX INTEGER
			MAX-ACCESS read-only
			STATUS current
			DESCRIPTION
				"The largest number of card which chassis device. always 0 which single device."
			::= { eciESDeviceEntry 8 }

		
--  1.3.6.1.4.1.25449.1.1.3.1.2.1.9
		-- 1.3.6.1.4.1.25449.1.1.3.1.2.1.9
		eciESDeviceCommand OBJECT-TYPE
			SYNTAX DisplayString
			MAX-ACCESS read-write
			STATUS current
			DESCRIPTION
				" "
			::= { eciESDeviceEntry 9 }

		
--  1.3.6.1.4.1.25449.1.1.3.1.2.1.10
		-- 1.3.6.1.4.1.25449.1.1.3.1.2.1.10
		eciESDeviceLoadCommand OBJECT-TYPE
			SYNTAX DisplayString
			MAX-ACCESS read-write
			STATUS current
			DESCRIPTION
				" "
			::= { eciESDeviceEntry 10 }

		
--  1.3.6.1.4.1.25449.1.1.3.1.2.1.11
		-- 1.3.6.1.4.1.25449.1.1.3.1.2.1.11
		eciESDeviceLightStatus OBJECT-TYPE
			SYNTAX OCTET STRING
			MAX-ACCESS read-write
			STATUS current
			DESCRIPTION
				" "
			::= { eciESDeviceEntry 11 }

		
--   card list entry   		
-- 1.3.6.1.4.1.25449.1.1.3.2
		-- 1.3.6.1.4.1.25449.1.1.3.2
		eciESCard OBJECT IDENTIFIER ::= { eciElementStructure 2 }

		
--  1.3.6.1.4.1.25449.1.1.3.2.1
		-- 1.3.6.1.4.1.25449.1.1.3.2.1
		eciESCardNumberTable OBJECT-TYPE
			SYNTAX SEQUENCE OF EciESCardNumberEntry
			MAX-ACCESS not-accessible
			STATUS current
			DESCRIPTION
				"card number table"
			::= { eciESCard 1 }

		
--  1.3.6.1.4.1.25449.1.1.3.2.1.1
		-- 1.3.6.1.4.1.25449.1.1.3.2.1.1
		eciESCardNumberEntry OBJECT-TYPE
			SYNTAX EciESCardNumberEntry
			MAX-ACCESS not-accessible
			STATUS current
			DESCRIPTION
				"card number table entry"
			INDEX { eciESDeviceIndex }
			::= { eciESCardNumberTable 1 }

		
		EciESCardNumberEntry ::=
			SEQUENCE { 
				eciESCardNumber
					INTEGER
			 }

--  1.3.6.1.4.1.25449.1.1.3.2.1.1.1
		-- 1.3.6.1.4.1.25449.1.1.3.2.1.1.1
		eciESCardNumber OBJECT-TYPE
			SYNTAX INTEGER
			MAX-ACCESS read-only
			STATUS current
			DESCRIPTION
				"numbers of cards which included by a element"
			::= { eciESCardNumberEntry 1 }

		
--  1.3.6.1.4.1.25449.1.1.3.2.2
		-- 1.3.6.1.4.1.25449.1.1.3.2.2
		eciESCardTable OBJECT-TYPE
			SYNTAX SEQUENCE OF EciESCardEntry
			MAX-ACCESS not-accessible
			STATUS current
			DESCRIPTION
				"card list table"
			::= { eciESCard 2 }

		
--  1.3.6.1.4.1.25449.1.1.3.2.2.1
		-- 1.3.6.1.4.1.25449.1.1.3.2.2.1
		eciESCardEntry OBJECT-TYPE
			SYNTAX EciESCardEntry
			MAX-ACCESS not-accessible
			STATUS current
			DESCRIPTION
				"card list table entry"
			INDEX { eciESDeviceIndex, eciESCardIndex }
			::= { eciESCardTable 1 }

		
		EciESCardEntry ::=
			SEQUENCE { 
				eciESCardIndex
					INTEGER,
				eciESCardUpDeviceIndex
					INTEGER,
				eciESCardName
					DisplayString,
				eciESCardType
					INTEGER,
				eciESCardDescr
					DisplayString,
				eciESCardSlotNumber
					INTEGER,
				eciESCardStatus
					INTEGER
			 }

--  1.3.6.1.4.1.25449.1.1.3.2.2.1.1
		-- 1.3.6.1.4.1.25449.1.1.3.2.2.1.1
		eciESCardIndex OBJECT-TYPE
			SYNTAX INTEGER
			MAX-ACCESS read-only
			STATUS current
			DESCRIPTION
				"card unique index"
			::= { eciESCardEntry 1 }

		
--  1.3.6.1.4.1.25449.1.1.3.2.2.1.2
		-- 1.3.6.1.4.1.25449.1.1.3.2.2.1.2
		eciESCardUpDeviceIndex OBJECT-TYPE
			SYNTAX INTEGER
			MAX-ACCESS read-only
			STATUS current
			DESCRIPTION
				"device unique index which card-owned"
			::= { eciESCardEntry 2 }

		
--  1.3.6.1.4.1.25449.1.1.3.2.2.1.3
		-- 1.3.6.1.4.1.25449.1.1.3.2.2.1.3
		eciESCardName OBJECT-TYPE
			SYNTAX DisplayString (SIZE (0..31))
			MAX-ACCESS read-only
			STATUS current
			DESCRIPTION
				"card unique type name"
			::= { eciESCardEntry 3 }

		
--  1.3.6.1.4.1.25449.1.1.3.2.2.1.4
		-- 1.3.6.1.4.1.25449.1.1.3.2.2.1.4
		eciESCardType OBJECT-TYPE
			SYNTAX INTEGER
			MAX-ACCESS read-only
			STATUS current
			DESCRIPTION
				"card unique type ID"
			::= { eciESCardEntry 4 }

		
--  1.3.6.1.4.1.25449.1.1.3.2.2.1.5
		-- 1.3.6.1.4.1.25449.1.1.3.2.2.1.5
		eciESCardDescr OBJECT-TYPE
			SYNTAX DisplayString (SIZE (0..31))
			MAX-ACCESS read-write
			STATUS current
			DESCRIPTION
				"card description"
			::= { eciESCardEntry 5 }

		
--  1.3.6.1.4.1.25449.1.1.3.2.2.1.6
		-- 1.3.6.1.4.1.25449.1.1.3.2.2.1.6
		eciESCardSlotNumber OBJECT-TYPE
			SYNTAX INTEGER
			MAX-ACCESS read-only
			STATUS current
			DESCRIPTION
				"slot number of card"
			::= { eciESCardEntry 6 }

		
--  1.3.6.1.4.1.25449.1.1.3.2.2.1.7
		-- 1.3.6.1.4.1.25449.1.1.3.2.2.1.7
		eciESCardStatus OBJECT-TYPE
			SYNTAX INTEGER
				{
				normal(1),
				fault(2),
				linkdown(3)
				}
			MAX-ACCESS read-only
			STATUS current
			DESCRIPTION
				"card status"
			::= { eciESCardEntry 7 }

		
--   connection list entry   	
-- 1.3.6.1.4.1.25449.1.1.3.5
		-- 1.3.6.1.4.1.25449.1.1.3.5
		eciESConnection OBJECT IDENTIFIER ::= { eciElementStructure 5 }

		
--  1.3.6.1.4.1.25449.1.1.3.5.1
		-- 1.3.6.1.4.1.25449.1.1.3.5.1
		eciESConnectionNumber OBJECT-TYPE
			SYNTAX INTEGER
			MAX-ACCESS read-only
			STATUS current
			DESCRIPTION
				"numbers of connection between devices"
			::= { eciESConnection 1 }

		
--  1.3.6.1.4.1.25449.1.1.3.5.2
		-- 1.3.6.1.4.1.25449.1.1.3.5.2
		eciESConnectionTable OBJECT-TYPE
			SYNTAX SEQUENCE OF EciESConnectionEntry
			MAX-ACCESS not-accessible
			STATUS current
			DESCRIPTION
				"connection list table"
			::= { eciESConnection 2 }

		
--  1.3.6.1.4.1.25449.1.1.3.5.2.1
		-- 1.3.6.1.4.1.25449.1.1.3.5.2.1
		eciESConnectionEntry OBJECT-TYPE
			SYNTAX EciESConnectionEntry
			MAX-ACCESS not-accessible
			STATUS current
			DESCRIPTION
				"connection list table entry"
			INDEX { eciESConnectionIndex }
			::= { eciESConnectionTable 1 }

		
		EciESConnectionEntry ::=
			SEQUENCE { 
				eciESConnectionIndex
					INTEGER,
				eciESConnectionDescr
					DisplayString,
				eciESConnectionDirection
					INTEGER,
				eciESConnectionType
					INTEGER,
				eciESConnectionAPointDeviceIndex
					INTEGER,
				eciESConnectionZPointDeviceIndex
					INTEGER,
				eciESConnectionAPointIFIndex
					INTEGER,
				eciESConnectionZPointIFIndex
					INTEGER
			 }

--  1.3.6.1.4.1.25449.1.1.3.5.2.1.1
		-- 1.3.6.1.4.1.25449.1.1.3.5.2.1.1
		eciESConnectionIndex OBJECT-TYPE
			SYNTAX INTEGER
			MAX-ACCESS read-only
			STATUS current
			DESCRIPTION
				"connection unique index"
			::= { eciESConnectionEntry 1 }

		
--  1.3.6.1.4.1.25449.1.1.3.5.2.1.2
		-- 1.3.6.1.4.1.25449.1.1.3.5.2.1.2
		eciESConnectionDescr OBJECT-TYPE
			SYNTAX DisplayString (SIZE (0..31))
			MAX-ACCESS read-write
			STATUS current
			DESCRIPTION
				"connection description"
			::= { eciESConnectionEntry 2 }

		
--  1.3.6.1.4.1.25449.1.1.3.5.2.1.3
		-- 1.3.6.1.4.1.25449.1.1.3.5.2.1.3
		eciESConnectionDirection OBJECT-TYPE
			SYNTAX INTEGER
				{
				dual(1),
				atoZ(2),
				ztoA(3)
				}
			MAX-ACCESS read-only
			STATUS current
			DESCRIPTION
				"connection direction"
			::= { eciESConnectionEntry 3 }

		
--  1.3.6.1.4.1.25449.1.1.3.5.2.1.4
		-- 1.3.6.1.4.1.25449.1.1.3.5.2.1.4
		eciESConnectionType OBJECT-TYPE
			SYNTAX INTEGER
				{
				logic(1),
				physical(2)
				}
			MAX-ACCESS read-only
			STATUS current
			DESCRIPTION
				"connection type"
			::= { eciESConnectionEntry 4 }

		
--  1.3.6.1.4.1.25449.1.1.3.5.2.1.5
		-- 1.3.6.1.4.1.25449.1.1.3.5.2.1.5
		eciESConnectionAPointDeviceIndex OBJECT-TYPE
			SYNTAX INTEGER
			MAX-ACCESS read-only
			STATUS current
			DESCRIPTION
				"A point device unique index"
			::= { eciESConnectionEntry 5 }

		
--  1.3.6.1.4.1.25449.1.1.3.5.2.1.6
		-- 1.3.6.1.4.1.25449.1.1.3.5.2.1.6
		eciESConnectionZPointDeviceIndex OBJECT-TYPE
			SYNTAX INTEGER
			MAX-ACCESS read-only
			STATUS current
			DESCRIPTION
				"Z point device unique index"
			::= { eciESConnectionEntry 6 }

		
--  1.3.6.1.4.1.25449.1.1.3.5.2.1.7
		-- 1.3.6.1.4.1.25449.1.1.3.5.2.1.7
		eciESConnectionAPointIFIndex OBJECT-TYPE
			SYNTAX INTEGER
			MAX-ACCESS read-only
			STATUS current
			DESCRIPTION
				"A point device connectiong interface index"
			::= { eciESConnectionEntry 7 }

		
--  1.3.6.1.4.1.25449.1.1.3.5.2.1.8
		-- 1.3.6.1.4.1.25449.1.1.3.5.2.1.8
		eciESConnectionZPointIFIndex OBJECT-TYPE
			SYNTAX INTEGER
			MAX-ACCESS read-only
			STATUS current
			DESCRIPTION
				"A point device connectiong interface index"
			::= { eciESConnectionEntry 8 }

		
	
	END

--
-- EZWELL-ELEMENTSTRUCTURE-MIB.mib
--
