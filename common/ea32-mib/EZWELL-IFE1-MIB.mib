--
-- EZWELL-IFE1-MIB.mib
-- MIB generated by MG-SOFT Visual MIB Builder Version 6.0  Build 88
-- Tuesday, January 17, 2017 at 17:04:00
--

	EZWELL-IFE1-MIB DEFINITIONS ::= BEGIN
 
		IMPORTS
			eciESDeviceIndex, eciESDeviceTypeName, eciESDeviceType, eciESDeviceName, eciESDeviceStatus, 
			eciESDeviceLocation, eciESDeviceIsChassis, eciESDeviceSlotNumber, eciESDeviceCommand, eciESDeviceLoadCommand, 
			eciESDeviceLightStatus			
				FROM EZWELL-ELEMENTSTRUCTURE-MIB			
			eciInterfaceModule			
				FROM EZWELL-GENERAL-MODEL-MIB			
			Integer32, Unsigned32, OBJECT-TYPE			
				FROM SNMPv2-SMI;
	
	
	
--
-- Node definitions
--
	
		-- 1.3.6.1.4.1.25449.1.1.8.7
		eciIFMdE1 OBJECT IDENTIFIER ::= { eciInterfaceModule 7 }

		
		-- 1.3.6.1.4.1.25449.1.1.8.7.1
		eciIfMdE1NumberTable OBJECT-TYPE
			SYNTAX SEQUENCE OF EciIfMdE1NumberEntry
			MAX-ACCESS not-accessible
			STATUS current
			DESCRIPTION
				"Description."
			::= { eciIFMdE1 1 }

		
		-- 1.3.6.1.4.1.25449.1.1.8.7.1.1
		eciIfMdE1NumberEntry OBJECT-TYPE
			SYNTAX EciIfMdE1NumberEntry
			MAX-ACCESS not-accessible
			STATUS current
			DESCRIPTION
				"Description."
			INDEX { eciESDeviceIndex }
			::= { eciIfMdE1NumberTable 1 }

		
		EciIfMdE1NumberEntry ::=
			SEQUENCE { 
				eciIfMdE1Number
					Integer32
			 }

		-- 1.3.6.1.4.1.25449.1.1.8.7.1.1.1
		eciIfMdE1Number OBJECT-TYPE
			SYNTAX Integer32
			MAX-ACCESS read-only
			STATUS current
			DESCRIPTION
				"Description."
			::= { eciIfMdE1NumberEntry 1 }

		
		-- 1.3.6.1.4.1.25449.1.1.8.7.2
		eciIfMdE1InterfaceTable OBJECT-TYPE
			SYNTAX SEQUENCE OF EciIfMdE1InterfaceEntry
			MAX-ACCESS not-accessible
			STATUS current
			DESCRIPTION
				"Description."
			::= { eciIFMdE1 2 }

		
		-- 1.3.6.1.4.1.25449.1.1.8.7.2.1
		eciIfMdE1InterfaceEntry OBJECT-TYPE
			SYNTAX EciIfMdE1InterfaceEntry
			MAX-ACCESS not-accessible
			STATUS current
			DESCRIPTION
				"Description."
			INDEX { eciESDeviceIndex, eciIfMdE1InterfaceIndex }
			::= { eciIfMdE1InterfaceTable 1 }

		
		EciIfMdE1InterfaceEntry ::=
			SEQUENCE { 
				eciIfMdE1InterfaceIndex
					Unsigned32,
				eciIfMdE1InterfaceName
					OCTET STRING,
				eciIfMdE1InterfaceSerialN
					Integer32,
				eciIfMdE1InterfaceUpCardIndex
					Integer32,
				eciIfMdE1ChannelMappingIndex
					Integer32
			 }

		-- 1.3.6.1.4.1.25449.1.1.8.7.2.1.1
		eciIfMdE1InterfaceIndex OBJECT-TYPE
			SYNTAX Unsigned32
			MAX-ACCESS read-only
			STATUS current
			DESCRIPTION
				"Description."
			::= { eciIfMdE1InterfaceEntry 1 }

		
		-- 1.3.6.1.4.1.25449.1.1.8.7.2.1.2
		eciIfMdE1InterfaceName OBJECT-TYPE
			SYNTAX OCTET STRING
			MAX-ACCESS read-only
			STATUS current
			DESCRIPTION
				"Description."
			::= { eciIfMdE1InterfaceEntry 2 }

		
		-- 1.3.6.1.4.1.25449.1.1.8.7.2.1.3
		eciIfMdE1InterfaceSerialN OBJECT-TYPE
			SYNTAX Integer32 (1..16)
			MAX-ACCESS read-only
			STATUS current
			DESCRIPTION
				"Description."
			::= { eciIfMdE1InterfaceEntry 3 }

		
		-- 1.3.6.1.4.1.25449.1.1.8.7.2.1.4
		eciIfMdE1InterfaceUpCardIndex OBJECT-TYPE
			SYNTAX Integer32
			MAX-ACCESS read-only
			STATUS current
			DESCRIPTION
				"Description."
			::= { eciIfMdE1InterfaceEntry 4 }

		
		-- 1.3.6.1.4.1.25449.1.1.8.7.2.1.5
		eciIfMdE1ChannelMappingIndex OBJECT-TYPE
			SYNTAX Integer32
			MAX-ACCESS read-only
			STATUS current
			DESCRIPTION
				"Description."
			::= { eciIfMdE1InterfaceEntry 5 }

		
		-- 1.3.6.1.4.1.25449.1.1.8.7.3
		eciIfMdE1StatusTable OBJECT-TYPE
			SYNTAX SEQUENCE OF EciIfMdE1StatusEntry
			MAX-ACCESS not-accessible
			STATUS current
			DESCRIPTION
				"Description."
			::= { eciIFMdE1 3 }

		
		-- 1.3.6.1.4.1.25449.1.1.8.7.3.1
		eciIfMdE1StatusEntry OBJECT-TYPE
			SYNTAX EciIfMdE1StatusEntry
			MAX-ACCESS not-accessible
			STATUS current
			DESCRIPTION
				"Description."
			INDEX { eciESDeviceIndex, eciIfMdE1InterfaceIndex }
			::= { eciIfMdE1StatusTable 1 }

		
		EciIfMdE1StatusEntry ::=
			SEQUENCE { 
				eciIfMdE1StLOS
					INTEGER,
				eciIfMdE1StAIS
					INTEGER,
				eciIfMdE1StCodeError
					INTEGER,
				eciIfMdE1StLOF
					INTEGER,
				eciIfMdE1StRDI
					INTEGER,
				eciIfMdE1StCRC
					INTEGER,
				eciIfMdE1StLOOPIND
					INTEGER,
				eciIfMdE1StVCATERR
					INTEGER
			 }

		-- 1.3.6.1.4.1.25449.1.1.8.7.3.1.1
		eciIfMdE1StLOS OBJECT-TYPE
			SYNTAX INTEGER
				{
				normal(0),
				los(1)
				}
			MAX-ACCESS read-only
			STATUS current
			DESCRIPTION
				"Description."
			::= { eciIfMdE1StatusEntry 1 }

		
		-- 1.3.6.1.4.1.25449.1.1.8.7.3.1.2
		eciIfMdE1StAIS OBJECT-TYPE
			SYNTAX INTEGER
				{
				normal(0),
				ais(1)
				}
			MAX-ACCESS read-only
			STATUS current
			DESCRIPTION
				"Description."
			::= { eciIfMdE1StatusEntry 2 }

		
		-- 1.3.6.1.4.1.25449.1.1.8.7.3.1.3
		eciIfMdE1StCodeError OBJECT-TYPE
			SYNTAX INTEGER
				{
				normal(0),
				codeErr(1)
				}
			MAX-ACCESS read-only
			STATUS current
			DESCRIPTION
				"Description."
			::= { eciIfMdE1StatusEntry 3 }

		
		-- 1.3.6.1.4.1.25449.1.1.8.7.3.1.4
		eciIfMdE1StLOF OBJECT-TYPE
			SYNTAX INTEGER
				{
				normal(0),
				lof(1)
				}
			MAX-ACCESS read-only
			STATUS current
			DESCRIPTION
				"Description."
			::= { eciIfMdE1StatusEntry 4 }

		
		-- 1.3.6.1.4.1.25449.1.1.8.7.3.1.5
		eciIfMdE1StRDI OBJECT-TYPE
			SYNTAX INTEGER
				{
				normal(0),
				rdi(1)
				}
			MAX-ACCESS read-only
			STATUS current
			DESCRIPTION
				"Description."
			::= { eciIfMdE1StatusEntry 5 }

		
		-- 1.3.6.1.4.1.25449.1.1.8.7.3.1.6
		eciIfMdE1StCRC OBJECT-TYPE
			SYNTAX INTEGER
				{
				normal(0),
				crcErr(1)
				}
			MAX-ACCESS read-only
			STATUS current
			DESCRIPTION
				"Description."
			::= { eciIfMdE1StatusEntry 6 }

		
		-- 1.3.6.1.4.1.25449.1.1.8.7.3.1.7
		eciIfMdE1StLOOPIND OBJECT-TYPE
			SYNTAX INTEGER
				{
				normal(0),
				loop(1)
				}
			MAX-ACCESS read-only
			STATUS current
			DESCRIPTION
				"Description."
			::= { eciIfMdE1StatusEntry 7 }

		
		-- 1.3.6.1.4.1.25449.1.1.8.7.3.1.8
		eciIfMdE1StVCATERR OBJECT-TYPE
			SYNTAX INTEGER
				{
				normal(0),
				vcatErr(1)
				}
			MAX-ACCESS read-only
			STATUS current
			DESCRIPTION
				"Description."
			::= { eciIfMdE1StatusEntry 8 }

		
		-- 1.3.6.1.4.1.25449.1.1.8.7.4
		eciIfMdE1ConfigTable OBJECT-TYPE
			SYNTAX SEQUENCE OF EciIfMdE1ConfigEntry
			MAX-ACCESS not-accessible
			STATUS current
			DESCRIPTION
				"Description."
			::= { eciIFMdE1 4 }

		
		-- 1.3.6.1.4.1.25449.1.1.8.7.4.1
		eciIfMdE1ConfigEntry OBJECT-TYPE
			SYNTAX EciIfMdE1ConfigEntry
			MAX-ACCESS not-accessible
			STATUS current
			DESCRIPTION
				"Description."
			INDEX { eciESDeviceIndex, eciIfMdE1InterfaceIndex }
			::= { eciIfMdE1ConfigTable 1 }

		
		EciIfMdE1ConfigEntry ::=
			SEQUENCE { 
				eciIfMdE1CfEnable
					INTEGER,
				eciIfMdE1CfLoop
					INTEGER
			 }

		-- 1.3.6.1.4.1.25449.1.1.8.7.4.1.1
		eciIfMdE1CfEnable OBJECT-TYPE
			SYNTAX INTEGER
				{
				disable(0),
				enable(1)
				}
			MAX-ACCESS read-write
			STATUS current
			DESCRIPTION
				"Description."
			::= { eciIfMdE1ConfigEntry 1 }

		
		-- 1.3.6.1.4.1.25449.1.1.8.7.4.1.2
		eciIfMdE1CfLoop OBJECT-TYPE
			SYNTAX INTEGER
				{
				noLoop(0),
				loop(1)
				}
			MAX-ACCESS read-write
			STATUS current
			DESCRIPTION
				"Description."
			::= { eciIfMdE1ConfigEntry 2 }

		
	
	END

--
-- EZWELL-IFE1-MIB.mib
--
