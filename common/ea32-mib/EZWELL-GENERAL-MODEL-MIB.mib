--
-- EZWELL-GENERAL-MODEL-MIB.mib
-- MIB generated by MG-SOFT Visual MIB Builder Version 6.0  Build 88
-- Tuesday, July 28, 2015 at 17:31:05
--

--  Easy BroadBand Technology MIB VER 2.0 (date 2009.10.1)
-- 
-- Easy BroadBand Technology specific MIB for general model entry.
-- dated  2009.10.1
-- Version 2.0 

	EZWELL-GENERAL-MODEL-MIB DEFINITIONS ::= BEGIN
 
		IMPORTS
			enterprises			
				FROM RFC1155-SMI;
	
	
	
--
-- Node definitions
--
	
-- 	private OID
		-- 1.3.6.1.4.1.25449
		easybroadband OBJECT IDENTIFIER ::= { enterprises 25449 }

		
-- 	general entry
		-- 1.3.6.1.4.1.25449.1
		eciroot OBJECT IDENTIFIER ::= { easybroadband 1 }

		
-- 	general model entry
		-- 1.3.6.1.4.1.25449.1.1
		ecicomponent OBJECT IDENTIFIER ::= { eciroot 1 }

		
-- 	element structure model entry            
		-- 1.3.6.1.4.1.25449.1.1.3
		eciElementStructure OBJECT IDENTIFIER ::= { ecicomponent 3 }

		
-- 	element alarm model entry                    
		-- 1.3.6.1.4.1.25449.1.1.4
		eciAlarm OBJECT IDENTIFIER ::= { ecicomponent 4 }

		
-- 	element security model entry                
		-- 1.3.6.1.4.1.25449.1.1.5
		eciSecurity OBJECT IDENTIFIER ::= { ecicomponent 5 }

		
		-- 1.3.6.1.4.1.25449.1.1.6
		eciPerformance OBJECT IDENTIFIER ::= { ecicomponent 6 }

		
-- 	element performance model entry                
-- eciPerformance OBJECT IDENTIFIER  ::= { ecicomponent 6 }
-- element function model implement entry   
		-- 1.3.6.1.4.1.25449.1.1.7
		eciFunctionModule OBJECT IDENTIFIER ::= { ecicomponent 7 }

		
-- 	element interface or channel model implement entry    
		-- 1.3.6.1.4.1.25449.1.1.8
		eciInterfaceModule OBJECT IDENTIFIER ::= { ecicomponent 8 }

		
-- 	element device property implement entry     
		-- 1.3.6.1.4.1.25449.1.1.9
		eciDeviceProp OBJECT IDENTIFIER ::= { ecicomponent 9 }

		
-- 	element card property implement entry    
		-- 1.3.6.1.4.1.25449.1.1.10
		eciCardProp OBJECT IDENTIFIER ::= { ecicomponent 10 }

		
-- 	element data debug define entry    
		-- 1.3.6.1.4.1.25449.1.1.11
		eciAdvanceDebug OBJECT IDENTIFIER ::= { ecicomponent 11 }

		
-- 	element trap define entry    
		-- 1.3.6.1.4.1.25449.1.1.12
		eciTrap OBJECT IDENTIFIER ::= { ecicomponent 12 }

		
	
	END

--
-- EZWELL-GENERAL-MODEL-MIB.mib
--
