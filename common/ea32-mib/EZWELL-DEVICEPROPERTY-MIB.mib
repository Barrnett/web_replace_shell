--
-- EZWELL-DEVICEPROPERTY-MIB.mib
-- MIB generated by MG-SOFT Visual MIB Builder Version 6.0  Build 88
-- Thursday, October 08, 2015 at 01:01:22
--

--  EZWELL-DEVICEPROPERTY-MIB.mib
-- MIB generated by MG-SOFT Visual MIB Builder Version 6.0  Build 88
-- Friday, August 28, 2015 at 17:15:11
-- 
--  EZWELL-DEVICEPROPERTY-MIB.mib
-- MIB generated by MG-SOFT Visual MIB Builder Version 6.0  Build 88
-- Tuesday, August 18, 2015 at 11:45:09
-- 
--  EZWELL-DEVICEPROPERTY-MIB.mib
-- MIB generated by MG-SOFT Visual MIB Builder Version 6.0  Build 88
-- Monday, September 24, 2012 at 12:05:38
-- 
--  Easy BroadBand Technology MIB VER 2.0 (date 2009.10.1)
-- 
-- Easy BroadBand Technology specific MIB for element device property.
-- dated  2009.10.1
-- Version 2.0 

	EZWELL-DEVICEPROPERTY-MIB DEFINITIONS ::= BEGIN
 
		IMPORTS
			eciESDeviceIndex			
				FROM EZWELL-ELEMENTSTRUCTURE-MIB			
			eciDeviceProp			
				FROM EZWELL-GENERAL-MODEL-MIB			
			DisplayString, PhysAddress			
				FROM RFC1213-MIB			
			MacAddress			
				FROM RFC1230-MIB			
			TimeTicks, Integer32, Unsigned32, OBJECT-TYPE			
				FROM SNMPv2-SMI;
	
	
	
--
-- Node definitions
--
	
--  Node definitions
-- 
-- Node definitions
-- 
-- Node definitions
-- 
-- device basic property 
-- 1.3.6.1.4.1.25449.1.1.9.1
-- 1.3.6.1.4.1.25449.1.1.9.1
-- 1.3.6.1.4.1.25449.1.1.9.1
		-- 1.3.6.1.4.1.25449.1.1.9.1
		eciDPBasicTable OBJECT-TYPE
			SYNTAX SEQUENCE OF EciDPBasicEntry
			MAX-ACCESS not-accessible
			STATUS current
			DESCRIPTION
				"devices basic Property list table"
			::= { eciDeviceProp 1 }

		
--    1.3.6.1.4.1.25449.1.1.9.1.1
-- 1.3.6.1.4.1.25449.1.1.9.1.1
-- 1.3.6.1.4.1.25449.1.1.9.1.1
		-- 1.3.6.1.4.1.25449.1.1.9.1.1
		eciDPBasicEntry OBJECT-TYPE
			SYNTAX EciDPBasicEntry
			MAX-ACCESS not-accessible
			STATUS current
			DESCRIPTION
				"devices basic list table entry"
			INDEX { eciESDeviceIndex }
			::= { eciDPBasicTable 1 }

		
		EciDPBasicEntry ::=
			SEQUENCE { 
				eciDPBasicDeviceName
					DisplayString,
				eciDPBasicUser
					DisplayString,
				eciDPBasicDesc
					DisplayString,
				eciDPBasicOther
					DisplayString,
				eciDPBasicContact
					DisplayString,
				eciDPBasicLocation
					DisplayString,
				eciDPBasicSoftwareReset
					INTEGER,
				eciDPBasicHardwareReset
					INTEGER,
				eciDPBasicRestart
					INTEGER,
				eciDPBasicDefaultSetting
					INTEGER
			 }

--    1.3.6.1.4.1.25449.1.1.9.1.1.1
-- 1.3.6.1.4.1.25449.1.1.9.1.1.1
-- 1.3.6.1.4.1.25449.1.1.9.1.1.1
		-- 1.3.6.1.4.1.25449.1.1.9.1.1.1
		eciDPBasicDeviceName OBJECT-TYPE
			SYNTAX DisplayString (SIZE (0..31))
			MAX-ACCESS read-write
			STATUS current
			DESCRIPTION
				"device name"
			::= { eciDPBasicEntry 1 }

		
--    1.3.6.1.4.1.25449.1.1.9.1.1.2
-- 1.3.6.1.4.1.25449.1.1.9.1.1.2
-- 1.3.6.1.4.1.25449.1.1.9.1.1.2
		-- 1.3.6.1.4.1.25449.1.1.9.1.1.2
		eciDPBasicUser OBJECT-TYPE
			SYNTAX DisplayString (SIZE (0..31))
			MAX-ACCESS read-write
			STATUS current
			DESCRIPTION
				"user name"
			::= { eciDPBasicEntry 2 }

		
--    1.3.6.1.4.1.25449.1.1.9.1.1.3
-- 1.3.6.1.4.1.25449.1.1.9.1.1.3
-- 1.3.6.1.4.1.25449.1.1.9.1.1.3
		-- 1.3.6.1.4.1.25449.1.1.9.1.1.3
		eciDPBasicDesc OBJECT-TYPE
			SYNTAX DisplayString (SIZE (0..63))
			MAX-ACCESS read-write
			STATUS current
			DESCRIPTION
				"device describer"
			::= { eciDPBasicEntry 3 }

		
--    1.3.6.1.4.1.25449.1.1.9.1.1.4
-- 1.3.6.1.4.1.25449.1.1.9.1.1.4
-- 1.3.6.1.4.1.25449.1.1.9.1.1.4
		-- 1.3.6.1.4.1.25449.1.1.9.1.1.4
		eciDPBasicOther OBJECT-TYPE
			SYNTAX DisplayString (SIZE (0..63))
			MAX-ACCESS read-write
			STATUS current
			DESCRIPTION
				"device describer"
			::= { eciDPBasicEntry 4 }

		
--    1.3.6.1.4.1.25449.1.1.9.1.1.5
-- 1.3.6.1.4.1.25449.1.1.9.1.1.5
-- 1.3.6.1.4.1.25449.1.1.9.1.1.5
		-- 1.3.6.1.4.1.25449.1.1.9.1.1.5
		eciDPBasicContact OBJECT-TYPE
			SYNTAX DisplayString (SIZE (0..63))
			MAX-ACCESS read-write
			STATUS current
			DESCRIPTION
				" "
			::= { eciDPBasicEntry 5 }

		
--    1.3.6.1.4.1.25449.1.1.9.1.1.6
-- 1.3.6.1.4.1.25449.1.1.9.1.1.6
-- 1.3.6.1.4.1.25449.1.1.9.1.1.6
		-- 1.3.6.1.4.1.25449.1.1.9.1.1.6
		eciDPBasicLocation OBJECT-TYPE
			SYNTAX DisplayString (SIZE (0..63))
			MAX-ACCESS read-write
			STATUS current
			DESCRIPTION
				" "
			::= { eciDPBasicEntry 6 }

		
--    1.3.6.1.4.1.25449.1.1.9.1.1.7
-- 1.3.6.1.4.1.25449.1.1.9.1.1.7
-- 1.3.6.1.4.1.25449.1.1.9.1.1.7
		-- 1.3.6.1.4.1.25449.1.1.9.1.1.7
		eciDPBasicSoftwareReset OBJECT-TYPE
			SYNTAX INTEGER { reset(4538946) }
			MAX-ACCESS read-write
			STATUS current
			DESCRIPTION
				" "
			::= { eciDPBasicEntry 7 }

		
--    1.3.6.1.4.1.25449.1.1.9.1.1.8
-- 1.3.6.1.4.1.25449.1.1.9.1.1.8
-- 1.3.6.1.4.1.25449.1.1.9.1.1.8
		-- 1.3.6.1.4.1.25449.1.1.9.1.1.8
		eciDPBasicHardwareReset OBJECT-TYPE
			SYNTAX INTEGER { reset(4538946) }
			MAX-ACCESS read-write
			STATUS current
			DESCRIPTION
				" "
			::= { eciDPBasicEntry 8 }

		
--    1.3.6.1.4.1.25449.1.1.9.1.1.9
-- 1.3.6.1.4.1.25449.1.1.9.1.1.9
-- 1.3.6.1.4.1.25449.1.1.9.1.1.9
		-- 1.3.6.1.4.1.25449.1.1.9.1.1.9
		eciDPBasicRestart OBJECT-TYPE
			SYNTAX INTEGER { reset(4538946) }
			MAX-ACCESS read-write
			STATUS current
			DESCRIPTION
				" "
			::= { eciDPBasicEntry 9 }

		
--    1.3.6.1.4.1.25449.1.1.9.1.1.10
-- 1.3.6.1.4.1.25449.1.1.9.1.1.10
-- 1.3.6.1.4.1.25449.1.1.9.1.1.10
		-- 1.3.6.1.4.1.25449.1.1.9.1.1.10
		eciDPBasicDefaultSetting OBJECT-TYPE
			SYNTAX INTEGER { restoreDefaults(4538946) }
			MAX-ACCESS read-write
			STATUS current
			DESCRIPTION
				" "
			::= { eciDPBasicEntry 10 }

		
--     device communication property
-- 1.3.6.1.4.1.25449.1.1.9.2
-- 1.3.6.1.4.1.25449.1.1.9.2
-- 1.3.6.1.4.1.25449.1.1.9.2
		-- 1.3.6.1.4.1.25449.1.1.9.2
		eciDPCommTable OBJECT-TYPE
			SYNTAX SEQUENCE OF EciDPCommEntry
			MAX-ACCESS not-accessible
			STATUS current
			DESCRIPTION
				"devices Property list table"
			::= { eciDeviceProp 2 }

		
--    1.3.6.1.4.1.25449.1.1.9.2.1
-- 1.3.6.1.4.1.25449.1.1.9.2.1
-- 1.3.6.1.4.1.25449.1.1.9.2.1
		-- 1.3.6.1.4.1.25449.1.1.9.2.1
		eciDPCommEntry OBJECT-TYPE
			SYNTAX EciDPCommEntry
			MAX-ACCESS not-accessible
			STATUS current
			DESCRIPTION
				"devices list table entry"
			INDEX { eciESDeviceIndex }
			::= { eciDPCommTable 1 }

		
		EciDPCommEntry ::=
			SEQUENCE { 
				eciDPCommExternalIP
					PhysAddress,
				eciDPCommExternalMask
					PhysAddress,
				eciDPCommGateway
					PhysAddress,
				eciDPCommInternalIP
					PhysAddress,
				eciDPCommInternalMask
					PhysAddress,
				eciDPCommMACAddress
					MacAddress,
				eciDPCommBasePort
					INTEGER,
				eciDPCommTrapDestIP
					PhysAddress,
				eciDPCommInnerVID
					Integer32
			 }

--    1.3.6.1.4.1.25449.1.1.9.2.1.1
-- 1.3.6.1.4.1.25449.1.1.9.2.1.1
-- 1.3.6.1.4.1.25449.1.1.9.2.1.1
		-- 1.3.6.1.4.1.25449.1.1.9.2.1.1
		eciDPCommExternalIP OBJECT-TYPE
			SYNTAX PhysAddress
			MAX-ACCESS read-write
			STATUS current
			DESCRIPTION
				"external IP address"
			::= { eciDPCommEntry 1 }

		
--    1.3.6.1.4.1.25449.1.1.9.2.1.2
-- 1.3.6.1.4.1.25449.1.1.9.2.1.2
-- 1.3.6.1.4.1.25449.1.1.9.2.1.2
		-- 1.3.6.1.4.1.25449.1.1.9.2.1.2
		eciDPCommExternalMask OBJECT-TYPE
			SYNTAX PhysAddress
			MAX-ACCESS read-write
			STATUS current
			DESCRIPTION
				"external IP mask"
			::= { eciDPCommEntry 2 }

		
--    1.3.6.1.4.1.25449.1.1.9.2.1.3
-- 1.3.6.1.4.1.25449.1.1.9.2.1.3
-- 1.3.6.1.4.1.25449.1.1.9.2.1.3
		-- 1.3.6.1.4.1.25449.1.1.9.2.1.3
		eciDPCommGateway OBJECT-TYPE
			SYNTAX PhysAddress
			MAX-ACCESS read-write
			STATUS current
			DESCRIPTION
				"gateway IP address"
			::= { eciDPCommEntry 3 }

		
--    1.3.6.1.4.1.25449.1.1.9.2.1.4
-- 1.3.6.1.4.1.25449.1.1.9.2.1.4
-- 1.3.6.1.4.1.25449.1.1.9.2.1.4
		-- 1.3.6.1.4.1.25449.1.1.9.2.1.4
		eciDPCommInternalIP OBJECT-TYPE
			SYNTAX PhysAddress
			MAX-ACCESS read-write
			STATUS current
			DESCRIPTION
				"internal IP address"
			::= { eciDPCommEntry 4 }

		
--    1.3.6.1.4.1.25449.1.1.9.2.1.5
-- 1.3.6.1.4.1.25449.1.1.9.2.1.5
-- 1.3.6.1.4.1.25449.1.1.9.2.1.5
		-- 1.3.6.1.4.1.25449.1.1.9.2.1.5
		eciDPCommInternalMask OBJECT-TYPE
			SYNTAX PhysAddress
			MAX-ACCESS read-write
			STATUS current
			DESCRIPTION
				"internal IP mask"
			::= { eciDPCommEntry 5 }

		
--    1.3.6.1.4.1.25449.1.1.9.2.1.6
-- 1.3.6.1.4.1.25449.1.1.9.2.1.6
-- 1.3.6.1.4.1.25449.1.1.9.2.1.6
		-- 1.3.6.1.4.1.25449.1.1.9.2.1.6
		eciDPCommMACAddress OBJECT-TYPE
			SYNTAX MacAddress
			MAX-ACCESS read-write
			STATUS current
			DESCRIPTION
				"MAC address"
			::= { eciDPCommEntry 6 }

		
--    1.3.6.1.4.1.25449.1.1.9.2.1.7
-- 1.3.6.1.4.1.25449.1.1.9.2.1.7
-- 1.3.6.1.4.1.25449.1.1.9.2.1.7
		-- 1.3.6.1.4.1.25449.1.1.9.2.1.7
		eciDPCommBasePort OBJECT-TYPE
			SYNTAX INTEGER
			MAX-ACCESS read-write
			STATUS current
			DESCRIPTION
				"device base port"
			::= { eciDPCommEntry 7 }

		
--    1.3.6.1.4.1.25449.1.1.9.2.1.8
-- 1.3.6.1.4.1.25449.1.1.9.2.1.8
-- 1.3.6.1.4.1.25449.1.1.9.2.1.8
		-- 1.3.6.1.4.1.25449.1.1.9.2.1.8
		eciDPCommTrapDestIP OBJECT-TYPE
			SYNTAX PhysAddress
			MAX-ACCESS read-write
			STATUS current
			DESCRIPTION
				"trap destination IP address"
			::= { eciDPCommEntry 8 }

		
--    1.3.6.1.4.1.25449.1.1.9.2.1.9
-- 1.3.6.1.4.1.25449.1.1.9.2.1.9
-- 1.3.6.1.4.1.25449.1.1.9.2.1.9
		-- 1.3.6.1.4.1.25449.1.1.9.2.1.9
		eciDPCommInnerVID OBJECT-TYPE
			SYNTAX Integer32
			MAX-ACCESS read-write
			STATUS current
			DESCRIPTION
				"Description."
			::= { eciDPCommEntry 9 }

		
--     device datetime property
-- 1.3.6.1.4.1.25449.1.1.9.3
-- 1.3.6.1.4.1.25449.1.1.9.3
-- 1.3.6.1.4.1.25449.1.1.9.3
		-- 1.3.6.1.4.1.25449.1.1.9.3
		eciDPTimeTable OBJECT-TYPE
			SYNTAX SEQUENCE OF EciDPTimeEntry
			MAX-ACCESS not-accessible
			STATUS current
			DESCRIPTION
				" "
			::= { eciDeviceProp 3 }

		
--    1.3.6.1.4.1.25449.1.1.9.3.1
-- 1.3.6.1.4.1.25449.1.1.9.3.1
-- 1.3.6.1.4.1.25449.1.1.9.3.1
		-- 1.3.6.1.4.1.25449.1.1.9.3.1
		eciDPTimeEntry OBJECT-TYPE
			SYNTAX EciDPTimeEntry
			MAX-ACCESS not-accessible
			STATUS current
			DESCRIPTION
				" "
			INDEX { eciESDeviceIndex }
			::= { eciDPTimeTable 1 }

		
		EciDPTimeEntry ::=
			SEQUENCE { 
				eciDPCurrentTime
					INTEGER,
				eciDPBootUpTime
					INTEGER
			 }

--    1.3.6.1.4.1.25449.1.1.9.3.1.1
-- 1.3.6.1.4.1.25449.1.1.9.3.1.1
-- 1.3.6.1.4.1.25449.1.1.9.3.1.1
		-- 1.3.6.1.4.1.25449.1.1.9.3.1.1
		eciDPCurrentTime OBJECT-TYPE
			SYNTAX INTEGER
			MAX-ACCESS read-write
			STATUS current
			DESCRIPTION
				" "
			::= { eciDPTimeEntry 1 }

		
--    1.3.6.1.4.1.25449.1.1.9.3.1.2
-- 1.3.6.1.4.1.25449.1.1.9.3.1.2
-- 1.3.6.1.4.1.25449.1.1.9.3.1.2
		-- 1.3.6.1.4.1.25449.1.1.9.3.1.2
		eciDPBootUpTime OBJECT-TYPE
			SYNTAX INTEGER
			MAX-ACCESS read-only
			STATUS current
			DESCRIPTION
				" "
			::= { eciDPTimeEntry 2 }

		
--     device version table
-- 1.3.6.1.4.1.25449.1.1.9.4
-- 1.3.6.1.4.1.25449.1.1.9.4
-- 1.3.6.1.4.1.25449.1.1.9.4
		-- 1.3.6.1.4.1.25449.1.1.9.4
		eciDPVersionTable OBJECT-TYPE
			SYNTAX SEQUENCE OF EciDPVersionEntry
			MAX-ACCESS not-accessible
			STATUS current
			DESCRIPTION
				"devices time sync list table"
			::= { eciDeviceProp 4 }

		
--    1.3.6.1.4.1.25449.1.1.9.4.1
-- 1.3.6.1.4.1.25449.1.1.9.4.1
-- 1.3.6.1.4.1.25449.1.1.9.4.1
		-- 1.3.6.1.4.1.25449.1.1.9.4.1
		eciDPVersionEntry OBJECT-TYPE
			SYNTAX EciDPVersionEntry
			MAX-ACCESS not-accessible
			STATUS current
			DESCRIPTION
				"devices time sync list table entry"
			INDEX { eciESDeviceIndex, eciDPVersionIndex }
			::= { eciDPVersionTable 1 }

		
		EciDPVersionEntry ::=
			SEQUENCE { 
				eciDPVersionIndex
					INTEGER,
				eciDPVersionName
					DisplayString,
				eciDPVersionNumber
					DisplayString
			 }

--    1.3.6.1.4.1.25449.1.1.9.4.1.1
-- 1.3.6.1.4.1.25449.1.1.9.4.1.1
-- 1.3.6.1.4.1.25449.1.1.9.4.1.1
		-- 1.3.6.1.4.1.25449.1.1.9.4.1.1
		eciDPVersionIndex OBJECT-TYPE
			SYNTAX INTEGER (1..13 | 30000)
			MAX-ACCESS read-only
			STATUS current
			DESCRIPTION
				"device version index"
			::= { eciDPVersionEntry 1 }

		
--    1.3.6.1.4.1.25449.1.1.9.4.1.2
-- 1.3.6.1.4.1.25449.1.1.9.4.1.2
-- 1.3.6.1.4.1.25449.1.1.9.4.1.2
		-- 1.3.6.1.4.1.25449.1.1.9.4.1.2
		eciDPVersionName OBJECT-TYPE
			SYNTAX DisplayString (SIZE (0..15))
			MAX-ACCESS read-only
			STATUS current
			DESCRIPTION
				"device version name"
			::= { eciDPVersionEntry 2 }

		
--    1.3.6.1.4.1.25449.1.1.9.4.1.3
-- 1.3.6.1.4.1.25449.1.1.9.4.1.3
-- 1.3.6.1.4.1.25449.1.1.9.4.1.3
		-- 1.3.6.1.4.1.25449.1.1.9.4.1.3
		eciDPVersionNumber OBJECT-TYPE
			SYNTAX DisplayString (SIZE (0..15))
			MAX-ACCESS read-only
			STATUS current
			DESCRIPTION
				"FacToryData: year << 16 | month << 8 | day"
			::= { eciDPVersionEntry 3 }

		
--     SDH device property
-- 1.3.6.1.4.1.25449.1.1.9.5
-- 1.3.6.1.4.1.25449.1.1.9.5
-- 1.3.6.1.4.1.25449.1.1.9.5
		-- 1.3.6.1.4.1.25449.1.1.9.5
		eciDPSDH OBJECT IDENTIFIER ::= { eciDeviceProp 5 }

		
--     SDH device clock property
-- 1.3.6.1.4.1.25449.1.1.9.5.1
-- 1.3.6.1.4.1.25449.1.1.9.5.1
-- 1.3.6.1.4.1.25449.1.1.9.5.1
		-- 1.3.6.1.4.1.25449.1.1.9.5.1
		eciDPSDHClockSource OBJECT IDENTIFIER ::= { eciDPSDH 1 }

		
--    1.3.6.1.4.1.25449.1.1.9.5.1.1
-- 1.3.6.1.4.1.25449.1.1.9.5.1.1
-- 1.3.6.1.4.1.25449.1.1.9.5.1.1
		-- 1.3.6.1.4.1.25449.1.1.9.5.1.1
		eciDPSDHClockGlobalTable OBJECT-TYPE
			SYNTAX SEQUENCE OF EciDPSDHClockGlobalEntry
			MAX-ACCESS not-accessible
			STATUS current
			DESCRIPTION
				" "
			::= { eciDPSDHClockSource 1 }

		
--    1.3.6.1.4.1.25449.1.1.9.5.1.1.1
-- 1.3.6.1.4.1.25449.1.1.9.5.1.1.1
-- 1.3.6.1.4.1.25449.1.1.9.5.1.1.1
		-- 1.3.6.1.4.1.25449.1.1.9.5.1.1.1
		eciDPSDHClockGlobalEntry OBJECT-TYPE
			SYNTAX EciDPSDHClockGlobalEntry
			MAX-ACCESS not-accessible
			STATUS current
			DESCRIPTION
				" "
			INDEX { eciESDeviceIndex }
			::= { eciDPSDHClockGlobalTable 1 }

		
		EciDPSDHClockGlobalEntry ::=
			SEQUENCE { 
				eciDPSDHClkGlbForceSwitch
					INTEGER,
				eciDPSDHClkGlbManualSwitch
					INTEGER,
				eciDPSDHClkSwitchMode
					INTEGER,
				eciDPSDHClkSSMThreshold
					INTEGER
			 }

--    1.3.6.1.4.1.25449.1.1.9.5.1.1.1.1
-- 1.3.6.1.4.1.25449.1.1.9.5.1.1.1.1
-- 1.3.6.1.4.1.25449.1.1.9.5.1.1.1.1
		-- 1.3.6.1.4.1.25449.1.1.9.5.1.1.1.1
		eciDPSDHClkGlbForceSwitch OBJECT-TYPE
			SYNTAX INTEGER
				{
				disable(1),
				sTM1-1(2),
				sTM1-2(3),
				freeRun(4)
				}
			MAX-ACCESS read-write
			STATUS current
			DESCRIPTION
				" "
			::= { eciDPSDHClockGlobalEntry 1 }

		
--    1.3.6.1.4.1.25449.1.1.9.5.1.1.1.2
-- 1.3.6.1.4.1.25449.1.1.9.5.1.1.1.2
-- 1.3.6.1.4.1.25449.1.1.9.5.1.1.1.2
		-- 1.3.6.1.4.1.25449.1.1.9.5.1.1.1.2
		eciDPSDHClkGlbManualSwitch OBJECT-TYPE
			SYNTAX INTEGER
				{
				disable(1),
				stm1-1(2),
				stm1-2(3),
				freeRun(4)
				}
			MAX-ACCESS read-write
			STATUS current
			DESCRIPTION
				" "
			::= { eciDPSDHClockGlobalEntry 2 }

		
--    1.3.6.1.4.1.25449.1.1.9.5.1.1.1.3
-- 1.3.6.1.4.1.25449.1.1.9.5.1.1.1.3
-- 1.3.6.1.4.1.25449.1.1.9.5.1.1.1.3
		-- 1.3.6.1.4.1.25449.1.1.9.5.1.1.1.3
		eciDPSDHClkSwitchMode OBJECT-TYPE
			SYNTAX INTEGER
				{
				ssm(1),
				priority(2)
				}
			MAX-ACCESS read-write
			STATUS current
			DESCRIPTION
				" "
			::= { eciDPSDHClockGlobalEntry 3 }

		
--    1.3.6.1.4.1.25449.1.1.9.5.1.1.1.4
-- 1.3.6.1.4.1.25449.1.1.9.5.1.1.1.4
-- 1.3.6.1.4.1.25449.1.1.9.5.1.1.1.4
		-- 1.3.6.1.4.1.25449.1.1.9.5.1.1.1.4
		eciDPSDHClkSSMThreshold OBJECT-TYPE
			SYNTAX INTEGER
				{
				ql_prc(2),
				ql_unk(3),
				ql_ssu-a(4),
				ql_ssu-b(5),
				ql_sec(6),
				ql_dnu(7)
				}
			MAX-ACCESS read-write
			STATUS current
			DESCRIPTION
				" "
			::= { eciDPSDHClockGlobalEntry 4 }

		
--    1.3.6.1.4.1.25449.1.1.9.5.1.2
-- 1.3.6.1.4.1.25449.1.1.9.5.1.2
-- 1.3.6.1.4.1.25449.1.1.9.5.1.2
		-- 1.3.6.1.4.1.25449.1.1.9.5.1.2
		eciDPSDHClkSrcTable OBJECT-TYPE
			SYNTAX SEQUENCE OF EciDPSDHClkSrcEntry
			MAX-ACCESS not-accessible
			STATUS current
			DESCRIPTION
				" "
			::= { eciDPSDHClockSource 2 }

		
--    1.3.6.1.4.1.25449.1.1.9.5.1.2.1
-- 1.3.6.1.4.1.25449.1.1.9.5.1.2.1
-- 1.3.6.1.4.1.25449.1.1.9.5.1.2.1
		-- 1.3.6.1.4.1.25449.1.1.9.5.1.2.1
		eciDPSDHClkSrcEntry OBJECT-TYPE
			SYNTAX EciDPSDHClkSrcEntry
			MAX-ACCESS not-accessible
			STATUS current
			DESCRIPTION
				" "
			INDEX { eciESDeviceIndex, eciDPSDHClkSrcIndex }
			::= { eciDPSDHClkSrcTable 1 }

		
		EciDPSDHClkSrcEntry ::=
			SEQUENCE { 
				eciDPSDHClkSrcIndex
					INTEGER,
				eciDPSDHClkSrcEnable
					INTEGER,
				eciDPSDHClkSrcPriority
					INTEGER,
				eciDPSDHClkSrcReceive
					INTEGER,
				eciDPSDHClkSrcTransmit
					INTEGER,
				eciDPSDHClkSrcSwitchDelay
					INTEGER,
				eciDPSDHClkSrcRecoveryDelay
					INTEGER
			 }

--    1.3.6.1.4.1.25449.1.1.9.5.1.2.1.1
-- 1.3.6.1.4.1.25449.1.1.9.5.1.2.1.1
-- 1.3.6.1.4.1.25449.1.1.9.5.1.2.1.1
		-- 1.3.6.1.4.1.25449.1.1.9.5.1.2.1.1
		eciDPSDHClkSrcIndex OBJECT-TYPE
			SYNTAX INTEGER
				{
				stm1(1),
				stm2(2),
				freerun(64)
				}
			MAX-ACCESS read-only
			STATUS current
			DESCRIPTION
				" "
			::= { eciDPSDHClkSrcEntry 1 }

		
--    1.3.6.1.4.1.25449.1.1.9.5.1.2.1.2
-- 1.3.6.1.4.1.25449.1.1.9.5.1.2.1.2
-- 1.3.6.1.4.1.25449.1.1.9.5.1.2.1.2
		-- 1.3.6.1.4.1.25449.1.1.9.5.1.2.1.2
		eciDPSDHClkSrcEnable OBJECT-TYPE
			SYNTAX INTEGER
				{
				disable(0),
				enable(1)
				}
			MAX-ACCESS read-write
			STATUS current
			DESCRIPTION
				" "
			::= { eciDPSDHClkSrcEntry 2 }

		
--    1.3.6.1.4.1.25449.1.1.9.5.1.2.1.3
-- 1.3.6.1.4.1.25449.1.1.9.5.1.2.1.3
-- 1.3.6.1.4.1.25449.1.1.9.5.1.2.1.3
		-- 1.3.6.1.4.1.25449.1.1.9.5.1.2.1.3
		eciDPSDHClkSrcPriority OBJECT-TYPE
			SYNTAX INTEGER (1..15)
			MAX-ACCESS read-write
			STATUS current
			DESCRIPTION
				" "
			::= { eciDPSDHClkSrcEntry 3 }

		
--    1.3.6.1.4.1.25449.1.1.9.5.1.2.1.4
-- 1.3.6.1.4.1.25449.1.1.9.5.1.2.1.4
-- 1.3.6.1.4.1.25449.1.1.9.5.1.2.1.4
		-- 1.3.6.1.4.1.25449.1.1.9.5.1.2.1.4
		eciDPSDHClkSrcReceive OBJECT-TYPE
			SYNTAX INTEGER
				{
				actual_value(1),
				ql_prc(2),
				ql_unk(3),
				ql_ssu-a(4),
				ql_ssu-b(5),
				ql_sec(6),
				ql_dnu(7)
				}
			MAX-ACCESS read-write
			STATUS current
			DESCRIPTION
				" "
			::= { eciDPSDHClkSrcEntry 4 }

		
--    1.3.6.1.4.1.25449.1.1.9.5.1.2.1.5
-- 1.3.6.1.4.1.25449.1.1.9.5.1.2.1.5
-- 1.3.6.1.4.1.25449.1.1.9.5.1.2.1.5
		-- 1.3.6.1.4.1.25449.1.1.9.5.1.2.1.5
		eciDPSDHClkSrcTransmit OBJECT-TYPE
			SYNTAX INTEGER
				{
				auto(1),
				ql_prc(2),
				ql_unk(3),
				ql_ssu-a(4),
				ql_ssu-b(5),
				ql_sec(6),
				ql_dnu(7)
				}
			MAX-ACCESS read-write
			STATUS current
			DESCRIPTION
				" "
			::= { eciDPSDHClkSrcEntry 5 }

		
--    1.3.6.1.4.1.25449.1.1.9.5.1.2.1.6
-- 1.3.6.1.4.1.25449.1.1.9.5.1.2.1.6
-- 1.3.6.1.4.1.25449.1.1.9.5.1.2.1.6
		-- 1.3.6.1.4.1.25449.1.1.9.5.1.2.1.6
		eciDPSDHClkSrcSwitchDelay OBJECT-TYPE
			SYNTAX INTEGER (192..1200)
			UNITS "ms"
			MAX-ACCESS read-write
			STATUS current
			DESCRIPTION
				" "
			::= { eciDPSDHClkSrcEntry 6 }

		
--    1.3.6.1.4.1.25449.1.1.9.5.1.2.1.7
-- 1.3.6.1.4.1.25449.1.1.9.5.1.2.1.7
-- 1.3.6.1.4.1.25449.1.1.9.5.1.2.1.7
		-- 1.3.6.1.4.1.25449.1.1.9.5.1.2.1.7
		eciDPSDHClkSrcRecoveryDelay OBJECT-TYPE
			SYNTAX INTEGER (5..12)
			UNITS "min"
			MAX-ACCESS read-write
			STATUS current
			DESCRIPTION
				" "
			::= { eciDPSDHClkSrcEntry 7 }

		
--    1.3.6.1.4.1.25449.1.1.9.5.1.3
-- 1.3.6.1.4.1.25449.1.1.9.5.1.3
-- 1.3.6.1.4.1.25449.1.1.9.5.1.3
		-- 1.3.6.1.4.1.25449.1.1.9.5.1.3
		eciDPSDHClockStatusGlobalTable OBJECT-TYPE
			SYNTAX SEQUENCE OF EciDPSDHClockStatusGlobalEntry
			MAX-ACCESS not-accessible
			STATUS current
			DESCRIPTION
				" "
			::= { eciDPSDHClockSource 3 }

		
--    1.3.6.1.4.1.25449.1.1.9.5.1.3.1
-- 1.3.6.1.4.1.25449.1.1.9.5.1.3.1
-- 1.3.6.1.4.1.25449.1.1.9.5.1.3.1
		-- 1.3.6.1.4.1.25449.1.1.9.5.1.3.1
		eciDPSDHClockStatusGlobalEntry OBJECT-TYPE
			SYNTAX EciDPSDHClockStatusGlobalEntry
			MAX-ACCESS not-accessible
			STATUS current
			DESCRIPTION
				" "
			INDEX { eciESDeviceIndex, eciDPSDHClkSrcIndex }
			::= { eciDPSDHClockStatusGlobalTable 1 }

		
		EciDPSDHClockStatusGlobalEntry ::=
			SEQUENCE { 
				eciDPSDHClkStatGlbCurrent
					INTEGER,
				eciDPSDHClkStatGlbHighPro
					INTEGER,
				eciDPSDHClkStatGlbSwitchBefore
					INTEGER,
				eciDPSDHClkStatGlbSwitchState
					INTEGER,
				eciDPSDHClkStatGlbSwitchMode
					INTEGER,
				eciDPSDHClkStatGlbActingTime
					TimeTicks
			 }

--    1.3.6.1.4.1.25449.1.1.9.5.1.3.1.1
-- 1.3.6.1.4.1.25449.1.1.9.5.1.3.1.1
-- 1.3.6.1.4.1.25449.1.1.9.5.1.3.1.1
		-- 1.3.6.1.4.1.25449.1.1.9.5.1.3.1.1
		eciDPSDHClkStatGlbCurrent OBJECT-TYPE
			SYNTAX INTEGER
				{
				invalid(0),
				stm1-1(2),
				stm1-2(3),
				freeRun(4)
				}
			MAX-ACCESS read-only
			STATUS current
			DESCRIPTION
				" "
			::= { eciDPSDHClockStatusGlobalEntry 1 }

		
--    1.3.6.1.4.1.25449.1.1.9.5.1.3.1.2
-- 1.3.6.1.4.1.25449.1.1.9.5.1.3.1.2
-- 1.3.6.1.4.1.25449.1.1.9.5.1.3.1.2
		-- 1.3.6.1.4.1.25449.1.1.9.5.1.3.1.2
		eciDPSDHClkStatGlbHighPro OBJECT-TYPE
			SYNTAX INTEGER
				{
				invalid(0),
				stm1-1(2),
				stm1-2(3),
				freeRun(4)
				}
			MAX-ACCESS read-only
			STATUS current
			DESCRIPTION
				" "
			::= { eciDPSDHClockStatusGlobalEntry 2 }

		
--    1.3.6.1.4.1.25449.1.1.9.5.1.3.1.3
-- 1.3.6.1.4.1.25449.1.1.9.5.1.3.1.3
-- 1.3.6.1.4.1.25449.1.1.9.5.1.3.1.3
		-- 1.3.6.1.4.1.25449.1.1.9.5.1.3.1.3
		eciDPSDHClkStatGlbSwitchBefore OBJECT-TYPE
			SYNTAX INTEGER
				{
				invalid(0),
				stm1-1(2),
				stm1-2(3),
				freeRun(4)
				}
			MAX-ACCESS read-only
			STATUS current
			DESCRIPTION
				" "
			::= { eciDPSDHClockStatusGlobalEntry 3 }

		
--    1.3.6.1.4.1.25449.1.1.9.5.1.3.1.4
-- 1.3.6.1.4.1.25449.1.1.9.5.1.3.1.4
-- 1.3.6.1.4.1.25449.1.1.9.5.1.3.1.4
		-- 1.3.6.1.4.1.25449.1.1.9.5.1.3.1.4
		eciDPSDHClkStatGlbSwitchState OBJECT-TYPE
			SYNTAX INTEGER
				{
				forcedSwitching(1),
				manualSwitching(2),
				autoSwitching(3),
				ready_to_resume(4)
				}
			MAX-ACCESS read-only
			STATUS current
			DESCRIPTION
				" "
			::= { eciDPSDHClockStatusGlobalEntry 4 }

		
--    1.3.6.1.4.1.25449.1.1.9.5.1.3.1.5
-- 1.3.6.1.4.1.25449.1.1.9.5.1.3.1.5
-- 1.3.6.1.4.1.25449.1.1.9.5.1.3.1.5
		-- 1.3.6.1.4.1.25449.1.1.9.5.1.3.1.5
		eciDPSDHClkStatGlbSwitchMode OBJECT-TYPE
			SYNTAX INTEGER
				{
				tracking(1),
				freeRun(2),
				holding(3)
				}
			MAX-ACCESS read-only
			STATUS current
			DESCRIPTION
				" "
			::= { eciDPSDHClockStatusGlobalEntry 5 }

		
--    1.3.6.1.4.1.25449.1.1.9.5.1.3.1.6
-- 1.3.6.1.4.1.25449.1.1.9.5.1.3.1.6
-- 1.3.6.1.4.1.25449.1.1.9.5.1.3.1.6
		-- 1.3.6.1.4.1.25449.1.1.9.5.1.3.1.6
		eciDPSDHClkStatGlbActingTime OBJECT-TYPE
			SYNTAX TimeTicks
			MAX-ACCESS read-only
			STATUS current
			DESCRIPTION
				" "
			::= { eciDPSDHClockStatusGlobalEntry 6 }

		
--    1.3.6.1.4.1.25449.1.1.9.5.1.4
-- 1.3.6.1.4.1.25449.1.1.9.5.1.4
-- 1.3.6.1.4.1.25449.1.1.9.5.1.4
		-- 1.3.6.1.4.1.25449.1.1.9.5.1.4
		eciDPSDHClockStatusSrcTable OBJECT-TYPE
			SYNTAX SEQUENCE OF EciDPSDHClockStatusSrcEntry
			MAX-ACCESS not-accessible
			STATUS current
			DESCRIPTION
				" "
			::= { eciDPSDHClockSource 4 }

		
--    1.3.6.1.4.1.25449.1.1.9.5.1.4.1
-- 1.3.6.1.4.1.25449.1.1.9.5.1.4.1
-- 1.3.6.1.4.1.25449.1.1.9.5.1.4.1
		-- 1.3.6.1.4.1.25449.1.1.9.5.1.4.1
		eciDPSDHClockStatusSrcEntry OBJECT-TYPE
			SYNTAX EciDPSDHClockStatusSrcEntry
			MAX-ACCESS not-accessible
			STATUS current
			DESCRIPTION
				" "
			INDEX { eciESDeviceIndex, eciDPSDHClkSrcIndex }
			::= { eciDPSDHClockStatusSrcTable 1 }

		
		EciDPSDHClockStatusSrcEntry ::=
			SEQUENCE { 
				eciDPSDHClkStatSrcEnable
					INTEGER,
				eciDPSDHClkStatSrcSSMReceive
					INTEGER,
				eciDPSDHClkStatSrcPriority
					INTEGER
			 }

--    1.3.6.1.4.1.25449.1.1.9.5.1.4.1.1
-- 1.3.6.1.4.1.25449.1.1.9.5.1.4.1.1
-- 1.3.6.1.4.1.25449.1.1.9.5.1.4.1.1
		-- 1.3.6.1.4.1.25449.1.1.9.5.1.4.1.1
		eciDPSDHClkStatSrcEnable OBJECT-TYPE
			SYNTAX INTEGER
				{
				disable(0),
				enable(1)
				}
			MAX-ACCESS read-only
			STATUS current
			DESCRIPTION
				" "
			::= { eciDPSDHClockStatusSrcEntry 1 }

		
--    1.3.6.1.4.1.25449.1.1.9.5.1.4.1.2
-- 1.3.6.1.4.1.25449.1.1.9.5.1.4.1.2
-- 1.3.6.1.4.1.25449.1.1.9.5.1.4.1.2
		-- 1.3.6.1.4.1.25449.1.1.9.5.1.4.1.2
		eciDPSDHClkStatSrcSSMReceive OBJECT-TYPE
			SYNTAX INTEGER
				{
				ql_dnu(0),
				ql_prc(2),
				ql_unk(3),
				ql_ssut(4),
				ql_ssul(5),
				ql_sec(6)
				}
			MAX-ACCESS read-only
			STATUS current
			DESCRIPTION
				" "
			::= { eciDPSDHClockStatusSrcEntry 2 }

		
--    1.3.6.1.4.1.25449.1.1.9.5.1.4.1.3
-- 1.3.6.1.4.1.25449.1.1.9.5.1.4.1.3
-- 1.3.6.1.4.1.25449.1.1.9.5.1.4.1.3
		-- 1.3.6.1.4.1.25449.1.1.9.5.1.4.1.3
		eciDPSDHClkStatSrcPriority OBJECT-TYPE
			SYNTAX INTEGER (1..15)
			MAX-ACCESS read-only
			STATUS current
			DESCRIPTION
				" "
			::= { eciDPSDHClockStatusSrcEntry 3 }

		
--    1.3.6.1.4.1.25449.1.1.9.6
-- 1.3.6.1.4.1.25449.1.1.9.6
-- 1.3.6.1.4.1.25449.1.1.9.6
		-- 1.3.6.1.4.1.25449.1.1.9.6
		eciDPRouteTable OBJECT-TYPE
			SYNTAX SEQUENCE OF EciDPRouteEntry
			MAX-ACCESS not-accessible
			STATUS current
			DESCRIPTION
				" "
			::= { eciDeviceProp 6 }

		
--    1.3.6.1.4.1.25449.1.1.9.6.1
-- 1.3.6.1.4.1.25449.1.1.9.6.1
-- 1.3.6.1.4.1.25449.1.1.9.6.1
		-- 1.3.6.1.4.1.25449.1.1.9.6.1
		eciDPRouteEntry OBJECT-TYPE
			SYNTAX EciDPRouteEntry
			MAX-ACCESS not-accessible
			STATUS current
			DESCRIPTION
				" "
			INDEX { eciESDeviceIndex, eciESRouteIndex }
			::= { eciDPRouteTable 1 }

		
		EciDPRouteEntry ::=
			SEQUENCE { 
				eciESRouteIndex
					Unsigned32,
				eciESRouteMAC
					MacAddress,
				eciESRouteIP
					PhysAddress,
				eciESRouteChannel
					INTEGER,
				eciESRouteHopCount
					INTEGER,
				eciESRouteAgingCount
					INTEGER,
				eciESRouteDeviceType
					INTEGER,
				eciESRouteDeviceSubType
					INTEGER,
				eciESRouteIsLocal
					INTEGER
			 }

--    1.3.6.1.4.1.25449.1.1.9.6.1.1
-- 1.3.6.1.4.1.25449.1.1.9.6.1.1
-- 1.3.6.1.4.1.25449.1.1.9.6.1.1
		-- 1.3.6.1.4.1.25449.1.1.9.6.1.1
		eciESRouteIndex OBJECT-TYPE
			SYNTAX Unsigned32 (0..4294967295)
			MAX-ACCESS read-only
			STATUS current
			DESCRIPTION
				" "
			::= { eciDPRouteEntry 1 }

		
--    1.3.6.1.4.1.25449.1.1.9.6.1.2
-- 1.3.6.1.4.1.25449.1.1.9.6.1.2
-- 1.3.6.1.4.1.25449.1.1.9.6.1.2
		-- 1.3.6.1.4.1.25449.1.1.9.6.1.2
		eciESRouteMAC OBJECT-TYPE
			SYNTAX MacAddress
			MAX-ACCESS read-only
			STATUS current
			DESCRIPTION
				" "
			::= { eciDPRouteEntry 2 }

		
--    1.3.6.1.4.1.25449.1.1.9.6.1.3
-- 1.3.6.1.4.1.25449.1.1.9.6.1.3
-- 1.3.6.1.4.1.25449.1.1.9.6.1.3
		-- 1.3.6.1.4.1.25449.1.1.9.6.1.3
		eciESRouteIP OBJECT-TYPE
			SYNTAX PhysAddress
			MAX-ACCESS read-only
			STATUS current
			DESCRIPTION
				" "
			::= { eciDPRouteEntry 3 }

		
--    1.3.6.1.4.1.25449.1.1.9.6.1.4
-- 1.3.6.1.4.1.25449.1.1.9.6.1.4
-- 1.3.6.1.4.1.25449.1.1.9.6.1.4
		-- 1.3.6.1.4.1.25449.1.1.9.6.1.4
		eciESRouteChannel OBJECT-TYPE
			SYNTAX INTEGER
			MAX-ACCESS read-only
			STATUS current
			DESCRIPTION
				" "
			::= { eciDPRouteEntry 4 }

		
--    1.3.6.1.4.1.25449.1.1.9.6.1.5
-- 1.3.6.1.4.1.25449.1.1.9.6.1.5
-- 1.3.6.1.4.1.25449.1.1.9.6.1.5
		-- 1.3.6.1.4.1.25449.1.1.9.6.1.5
		eciESRouteHopCount OBJECT-TYPE
			SYNTAX INTEGER
			MAX-ACCESS read-only
			STATUS current
			DESCRIPTION
				" "
			::= { eciDPRouteEntry 5 }

		
--    1.3.6.1.4.1.25449.1.1.9.6.1.6
-- 1.3.6.1.4.1.25449.1.1.9.6.1.6
-- 1.3.6.1.4.1.25449.1.1.9.6.1.6
		-- 1.3.6.1.4.1.25449.1.1.9.6.1.6
		eciESRouteAgingCount OBJECT-TYPE
			SYNTAX INTEGER
			MAX-ACCESS read-only
			STATUS current
			DESCRIPTION
				" "
			::= { eciDPRouteEntry 6 }

		
--    1.3.6.1.4.1.25449.1.1.9.6.1.7
-- 1.3.6.1.4.1.25449.1.1.9.6.1.7
-- 1.3.6.1.4.1.25449.1.1.9.6.1.7
		-- 1.3.6.1.4.1.25449.1.1.9.6.1.7
		eciESRouteDeviceType OBJECT-TYPE
			SYNTAX INTEGER
			MAX-ACCESS read-only
			STATUS current
			DESCRIPTION
				" "
			::= { eciDPRouteEntry 7 }

		
--    1.3.6.1.4.1.25449.1.1.9.6.1.8
-- 1.3.6.1.4.1.25449.1.1.9.6.1.8
-- 1.3.6.1.4.1.25449.1.1.9.6.1.8
		-- 1.3.6.1.4.1.25449.1.1.9.6.1.8
		eciESRouteDeviceSubType OBJECT-TYPE
			SYNTAX INTEGER
			MAX-ACCESS read-only
			STATUS current
			DESCRIPTION
				" "
			::= { eciDPRouteEntry 8 }

		
--    1.3.6.1.4.1.25449.1.1.9.6.1.9
-- 1.3.6.1.4.1.25449.1.1.9.6.1.9
-- 1.3.6.1.4.1.25449.1.1.9.6.1.9
		-- 1.3.6.1.4.1.25449.1.1.9.6.1.9
		eciESRouteIsLocal OBJECT-TYPE
			SYNTAX INTEGER
			MAX-ACCESS read-only
			STATUS current
			DESCRIPTION
				" "
			::= { eciDPRouteEntry 9 }

		
	
	END

--
-- EZWELL-DEVICEPROPERTY-MIB.mib
--
