-- File Name : TIANCHUANG-UNS-MIB
-- Date      : Wed Oct 25 08:57:04 GMT 2017
-- Author    : AdventNet Agent Toolkit C Edition - MibEditor 6



TIANCHUANG-D4122-MIB	DEFINITIONS ::= BEGIN
	IMPORTS
		RowStatus, DateAndTime
			FROM SNMPv2-TC
		enterprises, MODULE-IDENTITY, OBJECT-TYPE, Integer32, Counter64, TimeTicks, IpAddress, NOTIFICATION-TYPE
			FROM SNMPv2-SMI;

	company	MODULE-IDENTITY
		LAST-UPDATED	"201610300735Z"
		ORGANIZATION	"Organization"
		CONTACT-INFO	"Contact-info"
		DESCRIPTION		"Description"
		REVISION		"201610300735Z"
		DESCRIPTION		""
		::=  {  enterprises  1960  }

	org	OBJECT IDENTIFIER
		::=  {  iso  3  }

	dod	OBJECT IDENTIFIER
		::=  {  org  6  }

	internet	OBJECT IDENTIFIER
		::=  {  dod  1  }

	private	OBJECT IDENTIFIER
		::=  {  internet  4  }

	enterprises	OBJECT IDENTIFIER
		::=  {  private  1  }

	neMgmt	OBJECT IDENTIFIER
		::=  {  company  1  }

	products	OBJECT IDENTIFIER
		::=  {  company  2  }

	neSystem	OBJECT IDENTIFIER
		::=  {  neMgmt  1  }

	uns	OBJECT IDENTIFIER
		::=  {  products  1  }

	neTrapHostTable	OBJECT-TYPE
		SYNTAX		SEQUENCE  OF  NeTrapHostEntry
		MAX-ACCESS	not-accessible
		STATUS		current
		DESCRIPTION	"Description"
		::=  { neSystem  1 }

	neTrapHostEntry	OBJECT-TYPE
		SYNTAX		NeTrapHostEntry
		MAX-ACCESS	not-accessible
		STATUS		current
		DESCRIPTION	"Row Description"
		INDEX		{  neTrapHostIndex  }
		::=  { neTrapHostTable 1 }

	NeTrapHostEntry  ::=  SEQUENCE {
		neTrapHostIndex  Integer32,
		neTrapHostAddr  IpAddress,
		neTrapHostPort  Integer32
		}


	neTrapHostIndex	OBJECT-TYPE	
		SYNTAX			Integer32
		MAX-ACCESS		not-accessible
		STATUS			current
		DESCRIPTION		"Column Description"
		::=  {  neTrapHostEntry  1  }


	neTrapHostAddr	OBJECT-TYPE	
		SYNTAX			IpAddress
		MAX-ACCESS		read-write
		STATUS			current
		DESCRIPTION		"Column Description"
		::=  {  neTrapHostEntry  2  }


	neTrapHostPort	OBJECT-TYPE	
		SYNTAX			Integer32
		MAX-ACCESS		read-write
		STATUS			current
		DESCRIPTION		"Column Description"
		::=  {  neTrapHostEntry  3  }

	d4122	OBJECT IDENTIFIER
		::=  {  uns  1  }

	system	OBJECT IDENTIFIER
		::=  {  d4122  1  }

	stats	OBJECT IDENTIFIER
		::=  {  d4122  3  }

	statistics	OBJECT IDENTIFIER
		::=  {  d4122  4  }

	trap	OBJECT IDENTIFIER
		::=  {  d4122  10  }

	cpuUsage	OBJECT-TYPE	
		SYNTAX			Integer32
		MAX-ACCESS		read-only
		STATUS			current
		DESCRIPTION		"Description"
		::=  {  system  10  }

	memUsed	OBJECT-TYPE	
		SYNTAX			Integer32
		MAX-ACCESS		read-only
		STATUS			current
		DESCRIPTION		"Description"
		::=  {  system  11  }

	memTotal	OBJECT-TYPE	
		SYNTAX			Integer32
		MAX-ACCESS		read-only
		STATUS			current
		DESCRIPTION		"Description"
		::=  {  system  12  }

	hddUsed	OBJECT-TYPE	
		SYNTAX			Integer32
		MAX-ACCESS		read-only
		STATUS			current
		DESCRIPTION		"Description"
		::=  {  system  13  }

	hddTotal	OBJECT-TYPE	
		SYNTAX			Integer32
		MAX-ACCESS		read-only
		STATUS			current
		DESCRIPTION		"Description"
		::=  {  system  14  }

	sysStartTime	OBJECT-TYPE	
		SYNTAX			DateAndTime
		MAX-ACCESS		read-only
		STATUS			current
		DESCRIPTION		"Description"
		::=  {  system  15  }

	sysUpTime	OBJECT-TYPE	
		SYNTAX			TimeTicks
		MAX-ACCESS		read-only
		STATUS			current
		DESCRIPTION		"Description"
		::=  {  system  16  }

	lanStatTable	OBJECT-TYPE
		SYNTAX		SEQUENCE  OF  LanStatEntry
		MAX-ACCESS	not-accessible
		STATUS		current
		DESCRIPTION	"Description"
		::=  { stats  1 }

	lanStatEntry	OBJECT-TYPE
		SYNTAX		LanStatEntry
		MAX-ACCESS	not-accessible
		STATUS		current
		DESCRIPTION	"Row Description"
		INDEX		{  lanIndex  }
		::=  { lanStatTable 1 }

	LanStatEntry  ::=  SEQUENCE {
		lanIndex  Integer32,
		lanLink  INTEGER
		}


	lanIndex	OBJECT-TYPE	
		SYNTAX			Integer32
		MAX-ACCESS		not-accessible
		STATUS			current
		DESCRIPTION		"Column Description"
		::=  {  lanStatEntry  1  }


	lanLink	OBJECT-TYPE	
		SYNTAX			INTEGER  { down ( 0 ) , speed10M ( 1 ) , speed100M ( 2 ) , speed1000M ( 3 ) } 
		MAX-ACCESS		read-only
		STATUS			current
		DESCRIPTION		"Column Description"
		::=  {  lanStatEntry  2  }

	e1StatTable	OBJECT-TYPE
		SYNTAX		SEQUENCE  OF  E1StatEntry
		MAX-ACCESS	not-accessible
		STATUS		current
		DESCRIPTION	"Description"
		::=  { stats  2 }

	e1StatEntry	OBJECT-TYPE
		SYNTAX		E1StatEntry
		MAX-ACCESS	not-accessible
		STATUS		current
		DESCRIPTION	"Row Description"
		INDEX		{  e1Index  }
		::=  { e1StatTable 1 }

	E1StatEntry  ::=  SEQUENCE {
		e1Index  Integer32,
		e1Alarm  OCTET STRING
		}


	e1Index	OBJECT-TYPE	
		SYNTAX			Integer32
		MAX-ACCESS		not-accessible
		STATUS			current
		DESCRIPTION		"Column Description"
		::=  {  e1StatEntry  1  }


	e1Alarm	OBJECT-TYPE	
		SYNTAX			OCTET STRING  ( SIZE ( 1  ) ) 
		MAX-ACCESS		read-only
		STATUS			current
		DESCRIPTION		"Byte_1: bit_1 E1LOS, bit_2 E1AIS, bit_3 E1LOOP, bit_4 E1MLOF,bit_5 RDI, bit_6 CRC.(bit from the right side to the left side. 1 for alarm, 0 for normal.)"
		::=  {  e1StatEntry  2  }

	tunnelStatTable	OBJECT-TYPE
		SYNTAX		SEQUENCE  OF  TunnelStatEntry
		MAX-ACCESS	not-accessible
		STATUS		current
		DESCRIPTION	"Description"
		::=  { stats  3 }

	tunnelStatEntry	OBJECT-TYPE
		SYNTAX		TunnelStatEntry
		MAX-ACCESS	not-accessible
		STATUS		current
		DESCRIPTION	"Row Description"
		INDEX		{  tunnelIdex  }
		::=  { tunnelStatTable 1 }

	TunnelStatEntry  ::=  SEQUENCE {
		tunnelIdex  Integer32,
		tunnelConnect  INTEGER
		}


	tunnelIdex	OBJECT-TYPE	
		SYNTAX			Integer32
		MAX-ACCESS		not-accessible
		STATUS			current
		DESCRIPTION		"Column Description"
		::=  {  tunnelStatEntry  1  }


	tunnelConnect	OBJECT-TYPE	
		SYNTAX			INTEGER  { off ( 0 ) , onStandby ( 1 ) , onService ( 2 ) } 
		MAX-ACCESS		read-only
		STATUS			current
		DESCRIPTION		"Column Description"
		::=  {  tunnelStatEntry  2  }

	serviceStatisticTable	OBJECT-TYPE
		SYNTAX		SEQUENCE  OF  ServiceStatisticEntry
		MAX-ACCESS	not-accessible
		STATUS		current
		DESCRIPTION	"Description"
		::=  { statistics  1 }

	serviceStatisticEntry	OBJECT-TYPE
		SYNTAX		ServiceStatisticEntry
		MAX-ACCESS	not-accessible
		STATUS		current
		DESCRIPTION	"Row Description"
		INDEX		{  serviceIndex  }
		::=  { serviceStatisticTable 1 }

	ServiceStatisticEntry  ::=  SEQUENCE {
		serviceIndex  Integer32,
		serviceID  Integer32,
		serviceUpBytes  Counter64,
		serviceUpPackets  Counter64
		}


	serviceIndex	OBJECT-TYPE	
		SYNTAX			Integer32
		MAX-ACCESS		not-accessible
		STATUS			current
		DESCRIPTION		"Column Description"
		::=  {  serviceStatisticEntry  1  }


	serviceID	OBJECT-TYPE	
		SYNTAX			Integer32
		MAX-ACCESS		read-only
		STATUS			current
		DESCRIPTION		"Column Description"
		::=  {  serviceStatisticEntry  2  }


	serviceUpBytes	OBJECT-TYPE	
		SYNTAX			Counter64
		MAX-ACCESS		read-only
		STATUS			current
		DESCRIPTION		"Column Description"
		::=  {  serviceStatisticEntry  3  }


	serviceUpPackets	OBJECT-TYPE	
		SYNTAX			Counter64
		MAX-ACCESS		read-only
		STATUS			current
		DESCRIPTION		"Column Description"
		::=  {  serviceStatisticEntry  4  }

	lanLinkInfoNot	NOTIFICATION-TYPE
		OBJECTS			{ lanLink }
		STATUS			current
		DESCRIPTION		"Description"
		::=  {  trap  1  }

	e1AlarmInfoNot	NOTIFICATION-TYPE
		OBJECTS			{ e1Alarm }
		STATUS			current
		DESCRIPTION		"Description"
		::=  {  trap  2  }

	tunnelConnectInfoNot	NOTIFICATION-TYPE
		OBJECTS			{ tunnelConnect }
		STATUS			current
		DESCRIPTION		"Description"
		::=  {  trap  3  }

END
